;;; DNIT V4 (secao no fim do arquivo): bocas BNAA em planta pelas tabelas
;;; do DNIT - tubulares BNAA 01-11 (+ 2.00/2.50/3.00 extrapolados) e
;;; celulares quadrados (BNAA 12-41).
;;; Comandos: BOCASCADDIN (bloco dinamico BOCA_DNIT_PLANTA_V4) e BOCASCADASTRO.
;;; ==========================================================================
;;; BocasBueiroDNIT.lsp
;;; Blocos dinamicos de bocas de bueiros tubulares de concreto
;;; Base: DNIT IPR-736 Emenda 3 - desenhos 6.4(a) BNAR, 6.5(a) BNAA,
;;;       6.6(a) BEAA 15, 6.7(a) BEAA 30, 6.8(a) BEAA 45
;;; Diametros 1,00 / 1,20 / 1,50 = tabelas do album
;;; Diametros 2,00 / 2,50 / 3,00 = EXTRAPOLADOS (sem respaldo do album DNIT)
;;;
;;; Comandos:
;;;   BOCASTESTE  - cria so o bloco BOCA_BNAR_PLANTA (rode primeiro p/ testar)
;;;   BOCASDNIT   - cria os 10 blocos dinamicos (5 tipos x planta/frontal)
;;;   BOCASBASE   - cria apenas os blocos estaticos (sem bloco dinamico)
;;;
;;; Rode num desenho NOVO e vazio (biblioteca). Unidade lida de INSUNITS:
;;;   6=metro (padrao Civil 3D), 5=centimetro, 4=milimetro, 0=assume metro.
;;;
;;; Insercao - PLANTA : no eixo do feixe de tubos, na face da testa onde o
;;;   bueiro chega. Bueiro ao longo de +Y, alas para -Y. Esconsas ja saem
;;;   com a testa girada; para esconsidade do outro lado use ESPELHAR.
;;; Insercao - FRONTAL: centro do feixe, na geratriz inferior (topo da soleira).
;;; ==========================================================================
(vl-load-com)

(defun bc:esc ( / u)
  (setq u (getvar "INSUNITS"))
  (cond ((= u 6) 0.01) ((= u 5) 1.0) ((= u 4) 10.0) (T 0.01)))

(defun bc:camada (nome cor lt)
  (if (not (tblsearch "LAYER" nome))
    (entmake (list '(0 . "LAYER") '(100 . "AcDbSymbolTableRecord")
                   '(100 . "AcDbLayerTableRecord") (cons 2 nome) '(70 . 0)
                   (cons 62 cor) (cons 6 lt)))))

(defun bc:tipolinha (lt)
  (if (not (tblsearch "LTYPE" lt))
    (vl-catch-all-apply 'vla-load
      (list (vla-get-linetypes (vla-get-activedocument (vlax-get-acad-object)))
            lt "acadiso.lin")))
  (if (tblsearch "LTYPE" lt) lt "Continuous"))

(defun bc:camadas ()
  (bc:camada "BOCA-CONCRETO" 7 "Continuous")
  (bc:camada "BOCA-SOLEIRA" 8 "Continuous")
  (bc:camada "BOCA-OCULTO" 1 (bc:tipolinha "DASHED"))
  (bc:camada "BOCA-EIXO" 5 (bc:tipolinha "CENTER")))

(defun bc:p (q e) (list (* e (car q)) (* e (cadr q)) 0.0))

(defun bc:ent-original (en e / tp lay pts c rx ry)
  (setq tp (car en) lay (cadr en))
  (cond
    ((= tp "P")
     (setq pts (cddr en))
     (entmake (append (list '(0 . "LWPOLYLINE") '(100 . "AcDbEntity") (cons 8 lay)
                            '(100 . "AcDbPolyline") (cons 90 (length pts)) '(70 . 1))
                      (mapcar '(lambda (q) (list 10 (* e (car q)) (* e (cadr q)))) pts))))
    ((= tp "L")
     (entmake (list '(0 . "LINE") (cons 8 lay)
                    (cons 10 (bc:p (caddr en) e)) (cons 11 (bc:p (cadddr en) e)))))
    ((= tp "E")
     (setq c (caddr en) rx (* e (nth 3 en)) ry (* e (nth 4 en)))
     (if (equal rx ry 1e-9)
       (entmake (list '(0 . "CIRCLE") (cons 8 lay) (cons 10 (bc:p c e)) (cons 40 rx)))
       (entmake (list '(0 . "ELLIPSE") '(100 . "AcDbEntity") (cons 8 lay)
                      '(100 . "AcDbEllipse") (cons 10 (bc:p c e)) (list 11 rx 0.0 0.0)
                      '(210 0.0 0.0 1.0) (cons 40 (/ ry rx)) '(41 . 0.0)
                      (cons 42 (* 2.0 pi))))))))

;; bloco estatico de uma variante
(defun bc:bloco-base (nome ents e / en)
  (if (not (tblsearch "BLOCK" nome))
    (progn
      (entmake (list '(0 . "BLOCK") (cons 2 nome) '(70 . 0) '(8 . "0") '(10 0.0 0.0 0.0)))
      (foreach en ents (bc:ent en e))
      (entmake '((0 . "ENDBLK") (8 . "0")))))
  nome)

;; responde prompts restantes do comando ativo; cancela se nao terminar
(defun bc:fim (resp / i)
  (setq i 0)
  (while (and (> (getvar "CMDACTIVE") 0) (< i 4))
    (command resp) (setq i (1+ i)))
  (if (> (getvar "CMDACTIVE") 0) (command)))

;; bloco dinamico com parametro de visibilidade (um estado por variante)
(defun bc:bloco-dinamico (bnome estados e / lst)
  (if (tblsearch "BLOCK" bnome)
    (prompt (strcat "\n" bnome " ja existe - ignorado."))
    (progn
      (prompt (strcat "\nCriando " bnome " ..."))
      (foreach st estados (bc:bloco-base (cadr st) (caddr st) e))
      (entmake (list '(0 . "BLOCK") (cons 2 bnome) '(70 . 0) '(8 . "0") '(10 0.0 0.0 0.0)))
      (entmake (list '(0 . "POINT") '(8 . "Defpoints") '(10 0.0 0.0 0.0)))
      (entmake '((0 . "ENDBLK") (8 . "0")))
      (command "_.-BEDIT" bnome)
      (vl-catch-all-apply 'setvar (list "BVMODE" 1))
      (setq lst '())
      (foreach st estados
        (command "_.-INSERT" (cadr st) "_non" '(0.0 0.0 0.0) "1" "1" "0")
        (bc:fim "")
        (setq lst (cons (cons (car st) (entlast)) lst)))
      (setq lst (reverse lst))
      (command "_.BPARAMETER" "_V" "_non" (list 0.0 (* e 150.0) 0.0))
      (bc:fim "1")
      (foreach it lst
        (command "_.-BVSTATE" "_N" (car it) "_H")
        (bc:fim "")
        (command "_.BVSHOW" (cdr it) "")
        (bc:fim "_C"))
      (command "_.-BVSTATE" "_S" (car (car lst)))
      (bc:fim "")
      (command "_.-BVSTATE" "_D" "VisibilityState0")
      (bc:fim "_Y")
      (vl-catch-all-apply 'setvar (list "BVMODE" 0))
      (command "_.BSAVE")
      (bc:fim "")
      (command "_.BCLOSE")
      (bc:fim "_S")
      (prompt (strcat "\n  -> " bnome " criado com " (itoa (length lst)) " estados.")))))

(defun bc:executar (modo / *error* sv e)
  (setq sv (mapcar '(lambda (v) (cons v (getvar v))) '("CMDECHO" "OSMODE" "ATTREQ")))
  (defun *error* (msg)
    (foreach v sv (vl-catch-all-apply 'setvar (list (car v) (cdr v))))
    (if (not (wcmatch (strcase msg) "*CANCEL*,*QUIT*"))
      (prompt (strcat "\nErro: " msg
                      "\nSe o Editor de Blocos ficou aberto, feche com BCLOSE.")))
    (princ))
  (setvar "CMDECHO" 0) (setvar "OSMODE" 0) (setvar "ATTREQ" 0)
  (setq e (bc:esc))
  (if (= (getvar "INSUNITS") 0)
    (prompt "\nINSUNITS = 0 (sem unidade): assumindo desenho em METROS."))
  (bc:camadas)
  (cond
    ((= modo "TESTE")
     (bc:bloco-dinamico (car (car *bc:dados*)) (cadr (car *bc:dados*)) e))
    ((= modo "BASE")
     (foreach b *bc:dados*
       (foreach st (cadr b) (bc:bloco-base (cadr st) (caddr st) e)))
     (prompt "\nBlocos estaticos criados."))
    (T (foreach b *bc:dados* (bc:bloco-dinamico (car b) (cadr b) e))))
  (foreach v sv (setvar (car v) (cdr v)))
  (princ))

(defun c:BOCASTESTE () (bc:executar "TESTE"))
(defun c:BOCASDNIT () (bc:executar "TODOS"))
(defun c:BOCASBASE () (bc:executar "BASE"))

;;; ----------------------------- DADOS (cm) -------------------------------
(setq *bc:dados* (list
 (list "BOCA_BNAR_PLANTA" (list
  (list "BSTC 1,00 - BNAR 03" "BNAR_BSTC100_PL"
   '(("P" "BOCA-CONCRETO" (-85 0) (85 0) (85 -30) (-85 -30))
   ("P" "BOCA-CONCRETO" (-85 -30) (-65 -30) (-65 -195) (-85 -195))
   ("P" "BOCA-CONCRETO" (85 -30) (65 -30) (65 -195) (85 -195))
   ("P" "BOCA-SOLEIRA" (-95 0) (95 0) (95 -205) (-95 -205))
   ("L" "BOCA-OCULTO" (-50 0) (-50 -30))
   ("L" "BOCA-OCULTO" (50 0) (50 -30))
   ("L" "BOCA-EIXO" (0 60) (0 -70))))
  (list "BSTC 1,20 - BNAR 04" "BNAR_BSTC120_PL"
   '(("P" "BOCA-CONCRETO" (-100 0) (100 0) (100 -40) (-100 -40))
   ("P" "BOCA-CONCRETO" (-100 -40) (-80 -40) (-80 -220) (-100 -220))
   ("P" "BOCA-CONCRETO" (100 -40) (80 -40) (80 -220) (100 -220))
   ("P" "BOCA-SOLEIRA" (-110 0) (110 0) (110 -230) (-110 -230))
   ("L" "BOCA-OCULTO" (-60 0) (-60 -40))
   ("L" "BOCA-OCULTO" (60 0) (60 -40))
   ("L" "BOCA-EIXO" (0 60) (0 -80))))
  (list "BSTC 1,50 - BNAR 05" "BNAR_BSTC150_PL"
   '(("P" "BOCA-CONCRETO" (-120 0) (120 0) (120 -50) (-120 -50))
   ("P" "BOCA-CONCRETO" (-120 -50) (-100 -50) (-100 -310) (-120 -310))
   ("P" "BOCA-CONCRETO" (120 -50) (100 -50) (100 -310) (120 -310))
   ("P" "BOCA-SOLEIRA" (-130 0) (130 0) (130 -320) (-130 -320))
   ("L" "BOCA-OCULTO" (-75 0) (-75 -50))
   ("L" "BOCA-OCULTO" (75 0) (75 -50))
   ("L" "BOCA-EIXO" (0 60) (0 -90))))
  (list "BSTC 2,00 - EXTRAPOLADO" "BNAR_BSTC200_PL"
   '(("P" "BOCA-CONCRETO" (-160 0) (160 0) (160 -65) (-160 -65))
   ("P" "BOCA-CONCRETO" (-160 -65) (-135 -65) (-135 -410) (-160 -410))
   ("P" "BOCA-CONCRETO" (160 -65) (135 -65) (135 -410) (160 -410))
   ("P" "BOCA-SOLEIRA" (-170 0) (170 0) (170 -420) (-170 -420))
   ("L" "BOCA-OCULTO" (-100 0) (-100 -65))
   ("L" "BOCA-OCULTO" (100 0) (100 -65))
   ("L" "BOCA-EIXO" (0 60) (0 -105))))
  (list "BSTC 2,50 - EXTRAPOLADO" "BNAR_BSTC250_PL"
   '(("P" "BOCA-CONCRETO" (-200 0) (200 0) (200 -85) (-200 -85))
   ("P" "BOCA-CONCRETO" (-200 -85) (-175 -85) (-175 -520) (-200 -520))
   ("P" "BOCA-CONCRETO" (200 -85) (175 -85) (175 -520) (200 -520))
   ("P" "BOCA-SOLEIRA" (-210 0) (210 0) (210 -530) (-210 -530))
   ("L" "BOCA-OCULTO" (-125 0) (-125 -85))
   ("L" "BOCA-OCULTO" (125 0) (125 -85))
   ("L" "BOCA-EIXO" (0 60) (0 -125))))
  (list "BSTC 3,00 - EXTRAPOLADO" "BNAR_BSTC300_PL"
   '(("P" "BOCA-CONCRETO" (-240 0) (240 0) (240 -100) (-240 -100))
   ("P" "BOCA-CONCRETO" (-240 -100) (-210 -100) (-210 -620) (-240 -620))
   ("P" "BOCA-CONCRETO" (240 -100) (210 -100) (210 -620) (240 -620))
   ("P" "BOCA-SOLEIRA" (-250 0) (250 0) (250 -630) (-250 -630))
   ("L" "BOCA-OCULTO" (-150 0) (-150 -100))
   ("L" "BOCA-OCULTO" (150 0) (150 -100))
   ("L" "BOCA-EIXO" (0 60) (0 -140))))
  (list "BDTC 1,00 - BNAR 07" "BNAR_BDTC100_PL"
   '(("P" "BOCA-CONCRETO" (-160 0) (160 0) (160 -30) (-160 -30))
   ("P" "BOCA-CONCRETO" (-160 -30) (-140 -30) (-140 -195) (-160 -195))
   ("P" "BOCA-CONCRETO" (160 -30) (140 -30) (140 -195) (160 -195))
   ("P" "BOCA-SOLEIRA" (-170 0) (170 0) (170 -205) (-170 -205))
   ("L" "BOCA-OCULTO" (-126 0) (-126 -30))
   ("L" "BOCA-OCULTO" (-26 0) (-26 -30))
   ("L" "BOCA-OCULTO" (26 0) (26 -30))
   ("L" "BOCA-OCULTO" (126 0) (126 -30))
   ("L" "BOCA-EIXO" (0 60) (0 -70))))
  (list "BDTC 1,20 - BNAR 08" "BNAR_BDTC120_PL"
   '(("P" "BOCA-CONCRETO" (-185 0) (185 0) (185 -40) (-185 -40))
   ("P" "BOCA-CONCRETO" (-185 -40) (-165 -40) (-165 -220) (-185 -220))
   ("P" "BOCA-CONCRETO" (185 -40) (165 -40) (165 -220) (185 -220))
   ("P" "BOCA-SOLEIRA" (-195 0) (195 0) (195 -230) (-195 -230))
   ("L" "BOCA-OCULTO" (-149 0) (-149 -40))
   ("L" "BOCA-OCULTO" (-29 0) (-29 -40))
   ("L" "BOCA-OCULTO" (29 0) (29 -40))
   ("L" "BOCA-OCULTO" (149 0) (149 -40))
   ("L" "BOCA-EIXO" (0 60) (0 -80))))
  (list "BDTC 1,50 - BNAR 09" "BNAR_BDTC150_PL"
   '(("P" "BOCA-CONCRETO" (-217.5 0) (217.5 0) (217.5 -50) (-217.5 -50))
   ("P" "BOCA-CONCRETO" (-217.5 -50) (-197.5 -50) (-197.5 -310) (-217.5 -310))
   ("P" "BOCA-CONCRETO" (217.5 -50) (197.5 -50) (197.5 -310) (217.5 -310))
   ("P" "BOCA-SOLEIRA" (-227.5 0) (227.5 0) (227.5 -320) (-227.5 -320))
   ("L" "BOCA-OCULTO" (-181.5 0) (-181.5 -50))
   ("L" "BOCA-OCULTO" (-31.5 0) (-31.5 -50))
   ("L" "BOCA-OCULTO" (31.5 0) (31.5 -50))
   ("L" "BOCA-OCULTO" (181.5 0) (181.5 -50))
   ("L" "BOCA-EIXO" (0 60) (0 -90))))
  (list "BDTC 2,00 - EXTRAPOLADO" "BNAR_BDTC200_PL"
   '(("P" "BOCA-CONCRETO" (-284.5 0) (284.5 0) (284.5 -65) (-284.5 -65))
   ("P" "BOCA-CONCRETO" (-284.5 -65) (-259.5 -65) (-259.5 -410) (-284.5 -410))
   ("P" "BOCA-CONCRETO" (284.5 -65) (259.5 -65) (259.5 -410) (284.5 -410))
   ("P" "BOCA-SOLEIRA" (-294.5 0) (294.5 0) (294.5 -420) (-294.5 -420))
   ("L" "BOCA-OCULTO" (-236.5 0) (-236.5 -65))
   ("L" "BOCA-OCULTO" (-36.5 0) (-36.5 -65))
   ("L" "BOCA-OCULTO" (36.5 0) (36.5 -65))
   ("L" "BOCA-OCULTO" (236.5 0) (236.5 -65))
   ("L" "BOCA-EIXO" (0 60) (0 -105))))
  (list "BDTC 2,50 - EXTRAPOLADO" "BNAR_BDTC250_PL"
   '(("P" "BOCA-CONCRETO" (-351.5 0) (351.5 0) (351.5 -85) (-351.5 -85))
   ("P" "BOCA-CONCRETO" (-351.5 -85) (-326.5 -85) (-326.5 -520) (-351.5 -520))
   ("P" "BOCA-CONCRETO" (351.5 -85) (326.5 -85) (326.5 -520) (351.5 -520))
   ("P" "BOCA-SOLEIRA" (-361.5 0) (361.5 0) (361.5 -530) (-361.5 -530))
   ("L" "BOCA-OCULTO" (-291.5 0) (-291.5 -85))
   ("L" "BOCA-OCULTO" (-41.5 0) (-41.5 -85))
   ("L" "BOCA-OCULTO" (41.5 0) (41.5 -85))
   ("L" "BOCA-OCULTO" (291.5 0) (291.5 -85))
   ("L" "BOCA-EIXO" (0 60) (0 -125))))
  (list "BDTC 3,00 - EXTRAPOLADO" "BNAR_BDTC300_PL"
   '(("P" "BOCA-CONCRETO" (-418.5 0) (418.5 0) (418.5 -100) (-418.5 -100))
   ("P" "BOCA-CONCRETO" (-418.5 -100) (-388.5 -100) (-388.5 -620) (-418.5 -620))
   ("P" "BOCA-CONCRETO" (418.5 -100) (388.5 -100) (388.5 -620) (418.5 -620))
   ("P" "BOCA-SOLEIRA" (-428.5 0) (428.5 0) (428.5 -630) (-428.5 -630))
   ("L" "BOCA-OCULTO" (-346.5 0) (-346.5 -100))
   ("L" "BOCA-OCULTO" (-46.5 0) (-46.5 -100))
   ("L" "BOCA-OCULTO" (46.5 0) (46.5 -100))
   ("L" "BOCA-OCULTO" (346.5 0) (346.5 -100))
   ("L" "BOCA-EIXO" (0 60) (0 -140))))
  (list "BTTC 1,00 - BNAR 10" "BNAR_BTTC100_PL"
   '(("P" "BOCA-CONCRETO" (-235 0) (235 0) (235 -30) (-235 -30))
   ("P" "BOCA-CONCRETO" (-235 -30) (-215 -30) (-215 -195) (-235 -195))
   ("P" "BOCA-CONCRETO" (235 -30) (215 -30) (215 -195) (235 -195))
   ("P" "BOCA-SOLEIRA" (-245 0) (245 0) (245 -205) (-245 -205))
   ("L" "BOCA-OCULTO" (-203 0) (-203 -30))
   ("L" "BOCA-OCULTO" (-103 0) (-103 -30))
   ("L" "BOCA-OCULTO" (-50 0) (-50 -30))
   ("L" "BOCA-OCULTO" (50 0) (50 -30))
   ("L" "BOCA-OCULTO" (103 0) (103 -30))
   ("L" "BOCA-OCULTO" (203 0) (203 -30))
   ("L" "BOCA-EIXO" (0 60) (0 -70))))
  (list "BTTC 1,20 - BNAR 11" "BNAR_BTTC120_PL"
   '(("P" "BOCA-CONCRETO" (-272.5 0) (272.5 0) (272.5 -40) (-272.5 -40))
   ("P" "BOCA-CONCRETO" (-272.5 -40) (-252.5 -40) (-252.5 -220) (-272.5 -220))
   ("P" "BOCA-CONCRETO" (272.5 -40) (252.5 -40) (252.5 -220) (272.5 -220))
   ("P" "BOCA-SOLEIRA" (-282.5 0) (282.5 0) (282.5 -230) (-282.5 -230))
   ("L" "BOCA-OCULTO" (-237.5 0) (-237.5 -40))
   ("L" "BOCA-OCULTO" (-117.5 0) (-117.5 -40))
   ("L" "BOCA-OCULTO" (-60 0) (-60 -40))
   ("L" "BOCA-OCULTO" (60 0) (60 -40))
   ("L" "BOCA-OCULTO" (117.5 0) (117.5 -40))
   ("L" "BOCA-OCULTO" (237.5 0) (237.5 -40))
   ("L" "BOCA-EIXO" (0 60) (0 -80))))
  (list "BTTC 1,50 - BNAR 12" "BNAR_BTTC150_PL"
   '(("P" "BOCA-CONCRETO" (-325 0) (325 0) (325 -50) (-325 -50))
   ("P" "BOCA-CONCRETO" (-325 -50) (-305 -50) (-305 -310) (-325 -310))
   ("P" "BOCA-CONCRETO" (325 -50) (305 -50) (305 -310) (325 -310))
   ("P" "BOCA-SOLEIRA" (-335 0) (335 0) (335 -320) (-335 -320))
   ("L" "BOCA-OCULTO" (-288 0) (-288 -50))
   ("L" "BOCA-OCULTO" (-138 0) (-138 -50))
   ("L" "BOCA-OCULTO" (-75 0) (-75 -50))
   ("L" "BOCA-OCULTO" (75 0) (75 -50))
   ("L" "BOCA-OCULTO" (138 0) (138 -50))
   ("L" "BOCA-OCULTO" (288 0) (288 -50))
   ("L" "BOCA-EIXO" (0 60) (0 -90))))
  (list "BTTC 2,00 - EXTRAPOLADO" "BNAR_BTTC200_PL"
   '(("P" "BOCA-CONCRETO" (-422 0) (422 0) (422 -65) (-422 -65))
   ("P" "BOCA-CONCRETO" (-422 -65) (-397 -65) (-397 -410) (-422 -410))
   ("P" "BOCA-CONCRETO" (422 -65) (397 -65) (397 -410) (422 -410))
   ("P" "BOCA-SOLEIRA" (-432 0) (432 0) (432 -420) (-432 -420))
   ("L" "BOCA-OCULTO" (-373 0) (-373 -65))
   ("L" "BOCA-OCULTO" (-173 0) (-173 -65))
   ("L" "BOCA-OCULTO" (-100 0) (-100 -65))
   ("L" "BOCA-OCULTO" (100 0) (100 -65))
   ("L" "BOCA-OCULTO" (173 0) (173 -65))
   ("L" "BOCA-OCULTO" (373 0) (373 -65))
   ("L" "BOCA-EIXO" (0 60) (0 -105))))
  (list "BTTC 2,50 - EXTRAPOLADO" "BNAR_BTTC250_PL"
   '(("P" "BOCA-CONCRETO" (-520 0) (520 0) (520 -85) (-520 -85))
   ("P" "BOCA-CONCRETO" (-520 -85) (-495 -85) (-495 -520) (-520 -520))
   ("P" "BOCA-CONCRETO" (520 -85) (495 -85) (495 -520) (520 -520))
   ("P" "BOCA-SOLEIRA" (-530 0) (530 0) (530 -530) (-530 -530))
   ("L" "BOCA-OCULTO" (-458 0) (-458 -85))
   ("L" "BOCA-OCULTO" (-208 0) (-208 -85))
   ("L" "BOCA-OCULTO" (-125 0) (-125 -85))
   ("L" "BOCA-OCULTO" (125 0) (125 -85))
   ("L" "BOCA-OCULTO" (208 0) (208 -85))
   ("L" "BOCA-OCULTO" (458 0) (458 -85))
   ("L" "BOCA-EIXO" (0 60) (0 -125))))
  (list "BTTC 3,00 - EXTRAPOLADO" "BNAR_BTTC300_PL"
   '(("P" "BOCA-CONCRETO" (-617 0) (617 0) (617 -100) (-617 -100))
   ("P" "BOCA-CONCRETO" (-617 -100) (-587 -100) (-587 -620) (-617 -620))
   ("P" "BOCA-CONCRETO" (617 -100) (587 -100) (587 -620) (617 -620))
   ("P" "BOCA-SOLEIRA" (-627 0) (627 0) (627 -630) (-627 -630))
   ("L" "BOCA-OCULTO" (-543 0) (-543 -100))
   ("L" "BOCA-OCULTO" (-243 0) (-243 -100))
   ("L" "BOCA-OCULTO" (-150 0) (-150 -100))
   ("L" "BOCA-OCULTO" (150 0) (150 -100))
   ("L" "BOCA-OCULTO" (243 0) (243 -100))
   ("L" "BOCA-OCULTO" (543 0) (543 -100))
   ("L" "BOCA-EIXO" (0 60) (0 -140))))
 ))
 (list "BOCA_BNAR_FRONTAL" (list
  (list "BSTC 1,00 - BNAR 03" "BNAR_BSTC100_FR"
   '(("P" "BOCA-CONCRETO" (-85 0) (85 0) (85 142) (-85 142))
   ("E" "BOCA-CONCRETO" (0 50) 50 50)
   ("L" "BOCA-CONCRETO" (-65 0) (-65 142))
   ("L" "BOCA-CONCRETO" (-85 52) (-65 52))
   ("L" "BOCA-CONCRETO" (65 0) (65 142))
   ("L" "BOCA-CONCRETO" (85 52) (65 52))
   ("P" "BOCA-SOLEIRA" (-95 0) (95 0) (95 -65) (-95 -65))
   ("L" "BOCA-OCULTO" (-95 -25) (95 -25))
   ("P" "BOCA-SOLEIRA" (-95 -65) (95 -65) (95 -70) (-95 -70))))
  (list "BSTC 1,20 - BNAR 04" "BNAR_BSTC120_FR"
   '(("P" "BOCA-CONCRETO" (-100 0) (100 0) (100 163) (-100 163))
   ("E" "BOCA-CONCRETO" (0 60) 60 60)
   ("L" "BOCA-CONCRETO" (-80 0) (-80 163))
   ("L" "BOCA-CONCRETO" (-100 58) (-80 58))
   ("L" "BOCA-CONCRETO" (80 0) (80 163))
   ("L" "BOCA-CONCRETO" (100 58) (80 58))
   ("P" "BOCA-SOLEIRA" (-110 0) (110 0) (110 -65) (-110 -65))
   ("L" "BOCA-OCULTO" (-110 -25) (110 -25))
   ("P" "BOCA-SOLEIRA" (-110 -65) (110 -65) (110 -70) (-110 -70))))
  (list "BSTC 1,50 - BNAR 05" "BNAR_BSTC150_FR"
   '(("P" "BOCA-CONCRETO" (-120 0) (120 0) (120 194) (-120 194))
   ("E" "BOCA-CONCRETO" (0 75) 75 75)
   ("L" "BOCA-CONCRETO" (-100 0) (-100 194))
   ("L" "BOCA-CONCRETO" (-120 75) (-100 75))
   ("L" "BOCA-CONCRETO" (100 0) (100 194))
   ("L" "BOCA-CONCRETO" (120 75) (100 75))
   ("P" "BOCA-SOLEIRA" (-130 0) (130 0) (130 -70) (-130 -70))
   ("L" "BOCA-OCULTO" (-130 -30) (130 -30))
   ("P" "BOCA-SOLEIRA" (-130 -70) (130 -70) (130 -75) (-130 -75))))
  (list "BSTC 2,00 - EXTRAPOLADO" "BNAR_BSTC200_FR"
   '(("P" "BOCA-CONCRETO" (-160 0) (160 0) (160 244) (-160 244))
   ("E" "BOCA-CONCRETO" (0 100) 100 100)
   ("L" "BOCA-CONCRETO" (-135 0) (-135 244))
   ("L" "BOCA-CONCRETO" (-160 100) (-135 100))
   ("L" "BOCA-CONCRETO" (135 0) (135 244))
   ("L" "BOCA-CONCRETO" (160 100) (135 100))
   ("P" "BOCA-SOLEIRA" (-170 0) (170 0) (170 -80) (-170 -80))
   ("L" "BOCA-OCULTO" (-170 -35) (170 -35))
   ("P" "BOCA-SOLEIRA" (-170 -80) (170 -80) (170 -85) (-170 -85))))
  (list "BSTC 2,50 - EXTRAPOLADO" "BNAR_BSTC250_FR"
   '(("P" "BOCA-CONCRETO" (-200 0) (200 0) (200 294) (-200 294))
   ("E" "BOCA-CONCRETO" (0 125) 125 125)
   ("L" "BOCA-CONCRETO" (-175 0) (-175 294))
   ("L" "BOCA-CONCRETO" (-200 125) (-175 125))
   ("L" "BOCA-CONCRETO" (175 0) (175 294))
   ("L" "BOCA-CONCRETO" (200 125) (175 125))
   ("P" "BOCA-SOLEIRA" (-210 0) (210 0) (210 -90) (-210 -90))
   ("L" "BOCA-OCULTO" (-210 -40) (210 -40))
   ("P" "BOCA-SOLEIRA" (-210 -90) (210 -90) (210 -95) (-210 -95))))
  (list "BSTC 3,00 - EXTRAPOLADO" "BNAR_BSTC300_FR"
   '(("P" "BOCA-CONCRETO" (-240 0) (240 0) (240 344) (-240 344))
   ("E" "BOCA-CONCRETO" (0 150) 150 150)
   ("L" "BOCA-CONCRETO" (-210 0) (-210 344))
   ("L" "BOCA-CONCRETO" (-240 150) (-210 150))
   ("L" "BOCA-CONCRETO" (210 0) (210 344))
   ("L" "BOCA-CONCRETO" (240 150) (210 150))
   ("P" "BOCA-SOLEIRA" (-250 0) (250 0) (250 -95) (-250 -95))
   ("L" "BOCA-OCULTO" (-250 -40) (250 -40))
   ("P" "BOCA-SOLEIRA" (-250 -95) (250 -95) (250 -100) (-250 -100))))
  (list "BDTC 1,00 - BNAR 07" "BNAR_BDTC100_FR"
   '(("P" "BOCA-CONCRETO" (-160 0) (160 0) (160 142) (-160 142))
   ("E" "BOCA-CONCRETO" (-76 50) 50 50)
   ("E" "BOCA-CONCRETO" (76 50) 50 50)
   ("L" "BOCA-CONCRETO" (-140 0) (-140 142))
   ("L" "BOCA-CONCRETO" (-160 52) (-140 52))
   ("L" "BOCA-CONCRETO" (140 0) (140 142))
   ("L" "BOCA-CONCRETO" (160 52) (140 52))
   ("P" "BOCA-SOLEIRA" (-170 0) (170 0) (170 -65) (-170 -65))
   ("L" "BOCA-OCULTO" (-170 -25) (170 -25))
   ("P" "BOCA-SOLEIRA" (-170 -65) (170 -65) (170 -70) (-170 -70))))
  (list "BDTC 1,20 - BNAR 08" "BNAR_BDTC120_FR"
   '(("P" "BOCA-CONCRETO" (-185 0) (185 0) (185 163) (-185 163))
   ("E" "BOCA-CONCRETO" (-89 60) 60 60)
   ("E" "BOCA-CONCRETO" (89 60) 60 60)
   ("L" "BOCA-CONCRETO" (-165 0) (-165 163))
   ("L" "BOCA-CONCRETO" (-185 63) (-165 63))
   ("L" "BOCA-CONCRETO" (165 0) (165 163))
   ("L" "BOCA-CONCRETO" (185 63) (165 63))
   ("P" "BOCA-SOLEIRA" (-195 0) (195 0) (195 -65) (-195 -65))
   ("L" "BOCA-OCULTO" (-195 -25) (195 -25))
   ("P" "BOCA-SOLEIRA" (-195 -65) (195 -65) (195 -70) (-195 -70))))
  (list "BDTC 1,50 - BNAR 09" "BNAR_BDTC150_FR"
   '(("P" "BOCA-CONCRETO" (-217.5 0) (217.5 0) (217.5 194) (-217.5 194))
   ("E" "BOCA-CONCRETO" (-106.5 75) 75 75)
   ("E" "BOCA-CONCRETO" (106.5 75) 75 75)
   ("L" "BOCA-CONCRETO" (-197.5 0) (-197.5 194))
   ("L" "BOCA-CONCRETO" (-217.5 76) (-197.5 76))
   ("L" "BOCA-CONCRETO" (197.5 0) (197.5 194))
   ("L" "BOCA-CONCRETO" (217.5 76) (197.5 76))
   ("P" "BOCA-SOLEIRA" (-227.5 0) (227.5 0) (227.5 -70) (-227.5 -70))
   ("L" "BOCA-OCULTO" (-227.5 -30) (227.5 -30))
   ("P" "BOCA-SOLEIRA" (-227.5 -70) (227.5 -70) (227.5 -75) (-227.5 -75))))
  (list "BDTC 2,00 - EXTRAPOLADO" "BNAR_BDTC200_FR"
   '(("P" "BOCA-CONCRETO" (-284.5 0) (284.5 0) (284.5 244) (-284.5 244))
   ("E" "BOCA-CONCRETO" (-136.5 100) 100 100)
   ("E" "BOCA-CONCRETO" (136.5 100) 100 100)
   ("L" "BOCA-CONCRETO" (-259.5 0) (-259.5 244))
   ("L" "BOCA-CONCRETO" (-284.5 100) (-259.5 100))
   ("L" "BOCA-CONCRETO" (259.5 0) (259.5 244))
   ("L" "BOCA-CONCRETO" (284.5 100) (259.5 100))
   ("P" "BOCA-SOLEIRA" (-294.5 0) (294.5 0) (294.5 -80) (-294.5 -80))
   ("L" "BOCA-OCULTO" (-294.5 -35) (294.5 -35))
   ("P" "BOCA-SOLEIRA" (-294.5 -80) (294.5 -80) (294.5 -85) (-294.5 -85))))
  (list "BDTC 2,50 - EXTRAPOLADO" "BNAR_BDTC250_FR"
   '(("P" "BOCA-CONCRETO" (-351.5 0) (351.5 0) (351.5 294) (-351.5 294))
   ("E" "BOCA-CONCRETO" (-166.5 125) 125 125)
   ("E" "BOCA-CONCRETO" (166.5 125) 125 125)
   ("L" "BOCA-CONCRETO" (-326.5 0) (-326.5 294))
   ("L" "BOCA-CONCRETO" (-351.5 125) (-326.5 125))
   ("L" "BOCA-CONCRETO" (326.5 0) (326.5 294))
   ("L" "BOCA-CONCRETO" (351.5 125) (326.5 125))
   ("P" "BOCA-SOLEIRA" (-361.5 0) (361.5 0) (361.5 -90) (-361.5 -90))
   ("L" "BOCA-OCULTO" (-361.5 -40) (361.5 -40))
   ("P" "BOCA-SOLEIRA" (-361.5 -90) (361.5 -90) (361.5 -95) (-361.5 -95))))
  (list "BDTC 3,00 - EXTRAPOLADO" "BNAR_BDTC300_FR"
   '(("P" "BOCA-CONCRETO" (-418.5 0) (418.5 0) (418.5 344) (-418.5 344))
   ("E" "BOCA-CONCRETO" (-196.5 150) 150 150)
   ("E" "BOCA-CONCRETO" (196.5 150) 150 150)
   ("L" "BOCA-CONCRETO" (-388.5 0) (-388.5 344))
   ("L" "BOCA-CONCRETO" (-418.5 150) (-388.5 150))
   ("L" "BOCA-CONCRETO" (388.5 0) (388.5 344))
   ("L" "BOCA-CONCRETO" (418.5 150) (388.5 150))
   ("P" "BOCA-SOLEIRA" (-428.5 0) (428.5 0) (428.5 -95) (-428.5 -95))
   ("L" "BOCA-OCULTO" (-428.5 -40) (428.5 -40))
   ("P" "BOCA-SOLEIRA" (-428.5 -95) (428.5 -95) (428.5 -100) (-428.5 -100))))
  (list "BTTC 1,00 - BNAR 10" "BNAR_BTTC100_FR"
   '(("P" "BOCA-CONCRETO" (-235 0) (235 0) (235 142) (-235 142))
   ("E" "BOCA-CONCRETO" (-153 50) 50 50)
   ("E" "BOCA-CONCRETO" (0 50) 50 50)
   ("E" "BOCA-CONCRETO" (153 50) 50 50)
   ("L" "BOCA-CONCRETO" (-215 0) (-215 142))
   ("L" "BOCA-CONCRETO" (-235 52) (-215 52))
   ("L" "BOCA-CONCRETO" (215 0) (215 142))
   ("L" "BOCA-CONCRETO" (235 52) (215 52))
   ("P" "BOCA-SOLEIRA" (-245 0) (245 0) (245 -65) (-245 -65))
   ("L" "BOCA-OCULTO" (-245 -25) (245 -25))
   ("P" "BOCA-SOLEIRA" (-245 -65) (245 -65) (245 -70) (-245 -70))))
  (list "BTTC 1,20 - BNAR 11" "BNAR_BTTC120_FR"
   '(("P" "BOCA-CONCRETO" (-272.5 0) (272.5 0) (272.5 163) (-272.5 163))
   ("E" "BOCA-CONCRETO" (-177.5 60) 60 60)
   ("E" "BOCA-CONCRETO" (0 60) 60 60)
   ("E" "BOCA-CONCRETO" (177.5 60) 60 60)
   ("L" "BOCA-CONCRETO" (-252.5 0) (-252.5 163))
   ("L" "BOCA-CONCRETO" (-272.5 60) (-252.5 60))
   ("L" "BOCA-CONCRETO" (252.5 0) (252.5 163))
   ("L" "BOCA-CONCRETO" (272.5 60) (252.5 60))
   ("P" "BOCA-SOLEIRA" (-282.5 0) (282.5 0) (282.5 -65) (-282.5 -65))
   ("L" "BOCA-OCULTO" (-282.5 -25) (282.5 -25))
   ("P" "BOCA-SOLEIRA" (-282.5 -65) (282.5 -65) (282.5 -70) (-282.5 -70))))
  (list "BTTC 1,50 - BNAR 12" "BNAR_BTTC150_FR"
   '(("P" "BOCA-CONCRETO" (-325 0) (325 0) (325 194) (-325 194))
   ("E" "BOCA-CONCRETO" (-213 75) 75 75)
   ("E" "BOCA-CONCRETO" (0 75) 75 75)
   ("E" "BOCA-CONCRETO" (213 75) 75 75)
   ("L" "BOCA-CONCRETO" (-305 0) (-305 194))
   ("L" "BOCA-CONCRETO" (-325 80) (-305 80))
   ("L" "BOCA-CONCRETO" (305 0) (305 194))
   ("L" "BOCA-CONCRETO" (325 80) (305 80))
   ("P" "BOCA-SOLEIRA" (-335 0) (335 0) (335 -70) (-335 -70))
   ("L" "BOCA-OCULTO" (-335 -30) (335 -30))
   ("P" "BOCA-SOLEIRA" (-335 -70) (335 -70) (335 -75) (-335 -75))))
  (list "BTTC 2,00 - EXTRAPOLADO" "BNAR_BTTC200_FR"
   '(("P" "BOCA-CONCRETO" (-422 0) (422 0) (422 244) (-422 244))
   ("E" "BOCA-CONCRETO" (-273 100) 100 100)
   ("E" "BOCA-CONCRETO" (0 100) 100 100)
   ("E" "BOCA-CONCRETO" (273 100) 100 100)
   ("L" "BOCA-CONCRETO" (-397 0) (-397 244))
   ("L" "BOCA-CONCRETO" (-422 105) (-397 105))
   ("L" "BOCA-CONCRETO" (397 0) (397 244))
   ("L" "BOCA-CONCRETO" (422 105) (397 105))
   ("P" "BOCA-SOLEIRA" (-432 0) (432 0) (432 -80) (-432 -80))
   ("L" "BOCA-OCULTO" (-432 -35) (432 -35))
   ("P" "BOCA-SOLEIRA" (-432 -80) (432 -80) (432 -85) (-432 -85))))
  (list "BTTC 2,50 - EXTRAPOLADO" "BNAR_BTTC250_FR"
   '(("P" "BOCA-CONCRETO" (-520 0) (520 0) (520 294) (-520 294))
   ("E" "BOCA-CONCRETO" (-333 125) 125 125)
   ("E" "BOCA-CONCRETO" (0 125) 125 125)
   ("E" "BOCA-CONCRETO" (333 125) 125 125)
   ("L" "BOCA-CONCRETO" (-495 0) (-495 294))
   ("L" "BOCA-CONCRETO" (-520 135) (-495 135))
   ("L" "BOCA-CONCRETO" (495 0) (495 294))
   ("L" "BOCA-CONCRETO" (520 135) (495 135))
   ("P" "BOCA-SOLEIRA" (-530 0) (530 0) (530 -90) (-530 -90))
   ("L" "BOCA-OCULTO" (-530 -40) (530 -40))
   ("P" "BOCA-SOLEIRA" (-530 -90) (530 -90) (530 -95) (-530 -95))))
  (list "BTTC 3,00 - EXTRAPOLADO" "BNAR_BTTC300_FR"
   '(("P" "BOCA-CONCRETO" (-617 0) (617 0) (617 344) (-617 344))
   ("E" "BOCA-CONCRETO" (-393 150) 150 150)
   ("E" "BOCA-CONCRETO" (0 150) 150 150)
   ("E" "BOCA-CONCRETO" (393 150) 150 150)
   ("L" "BOCA-CONCRETO" (-587 0) (-587 344))
   ("L" "BOCA-CONCRETO" (-617 160) (-587 160))
   ("L" "BOCA-CONCRETO" (587 0) (587 344))
   ("L" "BOCA-CONCRETO" (617 160) (587 160))
   ("P" "BOCA-SOLEIRA" (-627 0) (627 0) (627 -95) (-627 -95))
   ("L" "BOCA-OCULTO" (-627 -40) (627 -40))
   ("P" "BOCA-SOLEIRA" (-627 -95) (627 -95) (627 -100) (-627 -100))))
 ))
 (list "BOCA_BNAA_PLANTA" (list
  (list "BSTC 1,00 - BNAA 03" "BNAA_BSTC100_PL"
   '(("P" "BOCA-CONCRETO" (-85 0) (85 0) (85 -30) (-85 -30))
   ("P" "BOCA-CONCRETO" (-85 -30) (-180.263 -195) (-157.169 -195) (-61.906 -30))
   ("P" "BOCA-CONCRETO" (85 -30) (180.263 -195) (157.169 -195) (61.906 -30))
   ("P" "BOCA-SOLEIRA" (-95 0) (95 0) (95 -30) (180.263 -195) (180.263 -205) (-180.263 -205) (-180.263 -195) (-95 -30))
   ("L" "BOCA-OCULTO" (-50 0) (-50 -30))
   ("L" "BOCA-OCULTO" (50 0) (50 -30))
   ("L" "BOCA-EIXO" (0 60) (0 -70))))
  (list "BSTC 1,20 - BNAA 04" "BNAA_BSTC120_PL"
   '(("P" "BOCA-CONCRETO" (-100 0) (100 0) (100 -40) (-100 -40))
   ("P" "BOCA-CONCRETO" (-100 -40) (-203.923 -220) (-180.829 -220) (-76.906 -40))
   ("P" "BOCA-CONCRETO" (100 -40) (203.923 -220) (180.829 -220) (76.906 -40))
   ("P" "BOCA-SOLEIRA" (-110 0) (110 0) (110 -40) (203.923 -220) (203.923 -230) (-203.923 -230) (-203.923 -220) (-110 -40))
   ("L" "BOCA-OCULTO" (-60 0) (-60 -40))
   ("L" "BOCA-OCULTO" (60 0) (60 -40))
   ("L" "BOCA-EIXO" (0 60) (0 -80))))
  (list "BSTC 1,50 - BNAA 05" "BNAA_BSTC150_PL"
   '(("P" "BOCA-CONCRETO" (-122.5 0) (122.5 0) (122.5 -50) (-122.5 -50))
   ("P" "BOCA-CONCRETO" (-122.5 -50) (-272.611 -310) (-249.517 -310) (-99.406 -50))
   ("P" "BOCA-CONCRETO" (122.5 -50) (272.611 -310) (249.517 -310) (99.406 -50))
   ("P" "BOCA-SOLEIRA" (-132.5 0) (132.5 0) (132.5 -50) (272.611 -310) (272.611 -320) (-272.611 -320) (-272.611 -310) (-132.5 -50))
   ("L" "BOCA-OCULTO" (-75.5 0) (-75.5 -50))
   ("L" "BOCA-OCULTO" (74.5 0) (74.5 -50))
   ("L" "BOCA-EIXO" (0 60) (0 -90))))
  (list "BSTC 2,00 - EXTRAPOLADO" "BNAA_BSTC200_PL"
   '(("P" "BOCA-CONCRETO" (-163 0) (163 0) (163 -65) (-163 -65))
   ("P" "BOCA-CONCRETO" (-163 -65) (-362.186 -410) (-333.318 -410) (-134.132 -65))
   ("P" "BOCA-CONCRETO" (163 -65) (362.186 -410) (333.318 -410) (134.132 -65))
   ("P" "BOCA-SOLEIRA" (-173 0) (173 0) (173 -65) (362.186 -410) (362.186 -420) (-362.186 -420) (-362.186 -410) (-173 -65))
   ("L" "BOCA-OCULTO" (-100 0) (-100 -65))
   ("L" "BOCA-OCULTO" (100 0) (100 -65))
   ("L" "BOCA-EIXO" (0 60) (0 -105))))
  (list "BSTC 2,50 - EXTRAPOLADO" "BNAA_BSTC250_PL"
   '(("P" "BOCA-CONCRETO" (-203 0) (203 0) (203 -85) (-203 -85))
   ("P" "BOCA-CONCRETO" (-203 -85) (-454.147 -520) (-425.28 -520) (-174.132 -85))
   ("P" "BOCA-CONCRETO" (203 -85) (454.147 -520) (425.28 -520) (174.132 -85))
   ("P" "BOCA-SOLEIRA" (-213 0) (213 0) (213 -85) (454.147 -520) (454.147 -530) (-454.147 -530) (-454.147 -520) (-213 -85))
   ("L" "BOCA-OCULTO" (-125 0) (-125 -85))
   ("L" "BOCA-OCULTO" (125 0) (125 -85))
   ("L" "BOCA-EIXO" (0 60) (0 -125))))
  (list "BSTC 3,00 - EXTRAPOLADO" "BNAA_BSTC300_PL"
   '(("P" "BOCA-CONCRETO" (-244 0) (244 0) (244 -100) (-244 -100))
   ("P" "BOCA-CONCRETO" (-244 -100) (-544.222 -620) (-509.581 -620) (-209.359 -100))
   ("P" "BOCA-CONCRETO" (244 -100) (544.222 -620) (509.581 -620) (209.359 -100))
   ("P" "BOCA-SOLEIRA" (-254 0) (254 0) (254 -100) (544.222 -620) (544.222 -630) (-544.222 -630) (-544.222 -620) (-254 -100))
   ("L" "BOCA-OCULTO" (-150 0) (-150 -100))
   ("L" "BOCA-OCULTO" (150 0) (150 -100))
   ("L" "BOCA-EIXO" (0 60) (0 -140))))
  (list "BDTC 1,00 - BNAA 06" "BNAA_BDTC100_PL"
   '(("P" "BOCA-CONCRETO" (-157.5 0) (157.5 0) (157.5 -30) (-157.5 -30))
   ("P" "BOCA-CONCRETO" (-157.5 -30) (-252.763 -195) (-229.669 -195) (-134.406 -30))
   ("P" "BOCA-CONCRETO" (157.5 -30) (252.763 -195) (229.669 -195) (134.406 -30))
   ("P" "BOCA-SOLEIRA" (-167.5 0) (167.5 0) (167.5 -30) (252.763 -195) (252.763 -205) (-252.763 -205) (-252.763 -195) (-167.5 -30))
   ("L" "BOCA-OCULTO" (-126.5 0) (-126.5 -30))
   ("L" "BOCA-OCULTO" (-26.5 0) (-26.5 -30))
   ("L" "BOCA-OCULTO" (26.5 0) (26.5 -30))
   ("L" "BOCA-OCULTO" (126.5 0) (126.5 -30))
   ("L" "BOCA-EIXO" (0 60) (0 -70))))
  (list "BDTC 1,20 - BNAA 07" "BNAA_BDTC120_PL"
   '(("P" "BOCA-CONCRETO" (-185 0) (185 0) (185 -40) (-185 -40))
   ("P" "BOCA-CONCRETO" (-185 -40) (-288.923 -220) (-265.829 -220) (-161.906 -40))
   ("P" "BOCA-CONCRETO" (185 -40) (288.923 -220) (265.829 -220) (161.906 -40))
   ("P" "BOCA-SOLEIRA" (-195 0) (195 0) (195 -40) (288.923 -220) (288.923 -230) (-288.923 -230) (-288.923 -220) (-195 -40))
   ("L" "BOCA-OCULTO" (-149 0) (-149 -40))
   ("L" "BOCA-OCULTO" (-29 0) (-29 -40))
   ("L" "BOCA-OCULTO" (29 0) (29 -40))
   ("L" "BOCA-OCULTO" (149 0) (149 -40))
   ("L" "BOCA-EIXO" (0 60) (0 -80))))
  (list "BDTC 1,50 - BNAA 08" "BNAA_BDTC150_PL"
   '(("P" "BOCA-CONCRETO" (-220 0) (220 0) (220 -50) (-220 -50))
   ("P" "BOCA-CONCRETO" (-220 -50) (-370.111 -310) (-347.017 -310) (-196.906 -50))
   ("P" "BOCA-CONCRETO" (220 -50) (370.111 -310) (347.017 -310) (196.906 -50))
   ("P" "BOCA-SOLEIRA" (-230 0) (230 0) (230 -50) (370.111 -310) (370.111 -320) (-370.111 -320) (-370.111 -310) (-230 -50))
   ("L" "BOCA-OCULTO" (-181 0) (-181 -50))
   ("L" "BOCA-OCULTO" (-31 0) (-31 -50))
   ("L" "BOCA-OCULTO" (31 0) (31 -50))
   ("L" "BOCA-OCULTO" (181 0) (181 -50))
   ("L" "BOCA-EIXO" (0 60) (0 -90))))
  (list "BDTC 2,00 - EXTRAPOLADO" "BNAA_BDTC200_PL"
   '(("P" "BOCA-CONCRETO" (-288.5 0) (288.5 0) (288.5 -65) (-288.5 -65))
   ("P" "BOCA-CONCRETO" (-288.5 -65) (-487.686 -410) (-458.818 -410) (-259.632 -65))
   ("P" "BOCA-CONCRETO" (288.5 -65) (487.686 -410) (458.818 -410) (259.632 -65))
   ("P" "BOCA-SOLEIRA" (-298.5 0) (298.5 0) (298.5 -65) (487.686 -410) (487.686 -420) (-487.686 -420) (-487.686 -410) (-298.5 -65))
   ("L" "BOCA-OCULTO" (-236.5 0) (-236.5 -65))
   ("L" "BOCA-OCULTO" (-36.5 0) (-36.5 -65))
   ("L" "BOCA-OCULTO" (36.5 0) (36.5 -65))
   ("L" "BOCA-OCULTO" (236.5 0) (236.5 -65))
   ("L" "BOCA-EIXO" (0 60) (0 -105))))
  (list "BDTC 2,50 - EXTRAPOLADO" "BNAA_BDTC250_PL"
   '(("P" "BOCA-CONCRETO" (-356.5 0) (356.5 0) (356.5 -85) (-356.5 -85))
   ("P" "BOCA-CONCRETO" (-356.5 -85) (-607.647 -520) (-578.78 -520) (-327.632 -85))
   ("P" "BOCA-CONCRETO" (356.5 -85) (607.647 -520) (578.78 -520) (327.632 -85))
   ("P" "BOCA-SOLEIRA" (-366.5 0) (366.5 0) (366.5 -85) (607.647 -520) (607.647 -530) (-607.647 -530) (-607.647 -520) (-366.5 -85))
   ("L" "BOCA-OCULTO" (-291.5 0) (-291.5 -85))
   ("L" "BOCA-OCULTO" (-41.5 0) (-41.5 -85))
   ("L" "BOCA-OCULTO" (41.5 0) (41.5 -85))
   ("L" "BOCA-OCULTO" (291.5 0) (291.5 -85))
   ("L" "BOCA-EIXO" (0 60) (0 -125))))
  (list "BDTC 3,00 - EXTRAPOLADO" "BNAA_BDTC300_PL"
   '(("P" "BOCA-CONCRETO" (-424.5 0) (424.5 0) (424.5 -100) (-424.5 -100))
   ("P" "BOCA-CONCRETO" (-424.5 -100) (-724.722 -620) (-690.081 -620) (-389.859 -100))
   ("P" "BOCA-CONCRETO" (424.5 -100) (724.722 -620) (690.081 -620) (389.859 -100))
   ("P" "BOCA-SOLEIRA" (-434.5 0) (434.5 0) (434.5 -100) (724.722 -620) (724.722 -630) (-724.722 -630) (-724.722 -620) (-434.5 -100))
   ("L" "BOCA-OCULTO" (-346.5 0) (-346.5 -100))
   ("L" "BOCA-OCULTO" (-46.5 0) (-46.5 -100))
   ("L" "BOCA-OCULTO" (46.5 0) (46.5 -100))
   ("L" "BOCA-OCULTO" (346.5 0) (346.5 -100))
   ("L" "BOCA-EIXO" (0 60) (0 -140))))
  (list "BTTC 1,00 - BNAA 09" "BNAA_BTTC100_PL"
   '(("P" "BOCA-CONCRETO" (-235 0) (235 0) (235 -30) (-235 -30))
   ("P" "BOCA-CONCRETO" (-235 -30) (-330.263 -195) (-307.169 -195) (-211.906 -30))
   ("P" "BOCA-CONCRETO" (235 -30) (330.263 -195) (307.169 -195) (211.906 -30))
   ("P" "BOCA-SOLEIRA" (-245 0) (245 0) (245 -30) (330.263 -195) (330.263 -205) (-330.263 -205) (-330.263 -195) (-245 -30))
   ("L" "BOCA-OCULTO" (-203 0) (-203 -30))
   ("L" "BOCA-OCULTO" (-103 0) (-103 -30))
   ("L" "BOCA-OCULTO" (-50 0) (-50 -30))
   ("L" "BOCA-OCULTO" (50 0) (50 -30))
   ("L" "BOCA-OCULTO" (103 0) (103 -30))
   ("L" "BOCA-OCULTO" (203 0) (203 -30))
   ("L" "BOCA-EIXO" (0 60) (0 -70))))
  (list "BTTC 1,20 - BNAA 10" "BNAA_BTTC120_PL"
   '(("P" "BOCA-CONCRETO" (-270 0) (270 0) (270 -40) (-270 -40))
   ("P" "BOCA-CONCRETO" (-270 -40) (-373.923 -220) (-350.829 -220) (-246.906 -40))
   ("P" "BOCA-CONCRETO" (270 -40) (373.923 -220) (350.829 -220) (246.906 -40))
   ("P" "BOCA-SOLEIRA" (-280 0) (280 0) (280 -40) (373.923 -220) (373.923 -230) (-373.923 -230) (-373.923 -220) (-280 -40))
   ("L" "BOCA-OCULTO" (-238 0) (-238 -40))
   ("L" "BOCA-OCULTO" (-118 0) (-118 -40))
   ("L" "BOCA-OCULTO" (-60 0) (-60 -40))
   ("L" "BOCA-OCULTO" (60 0) (60 -40))
   ("L" "BOCA-OCULTO" (118 0) (118 -40))
   ("L" "BOCA-OCULTO" (238 0) (238 -40))
   ("L" "BOCA-EIXO" (0 60) (0 -80))))
  (list "BTTC 1,50 - BNAA 11" "BNAA_BTTC150_PL"
   '(("P" "BOCA-CONCRETO" (-325 0) (325 0) (325 -50) (-325 -50))
   ("P" "BOCA-CONCRETO" (-325 -50) (-475.111 -310) (-452.017 -310) (-301.906 -50))
   ("P" "BOCA-CONCRETO" (325 -50) (475.111 -310) (452.017 -310) (301.906 -50))
   ("P" "BOCA-SOLEIRA" (-335 0) (335 0) (335 -50) (475.111 -310) (475.111 -320) (-475.111 -320) (-475.111 -310) (-335 -50))
   ("L" "BOCA-OCULTO" (-287 0) (-287 -50))
   ("L" "BOCA-OCULTO" (-137 0) (-137 -50))
   ("L" "BOCA-OCULTO" (-75 0) (-75 -50))
   ("L" "BOCA-OCULTO" (75 0) (75 -50))
   ("L" "BOCA-OCULTO" (137 0) (137 -50))
   ("L" "BOCA-OCULTO" (287 0) (287 -50))
   ("L" "BOCA-EIXO" (0 60) (0 -90))))
  (list "BTTC 2,00 - EXTRAPOLADO" "BNAA_BTTC200_PL"
   '(("P" "BOCA-CONCRETO" (-424 0) (424 0) (424 -65) (-424 -65))
   ("P" "BOCA-CONCRETO" (-424 -65) (-623.186 -410) (-594.318 -410) (-395.132 -65))
   ("P" "BOCA-CONCRETO" (424 -65) (623.186 -410) (594.318 -410) (395.132 -65))
   ("P" "BOCA-SOLEIRA" (-434 0) (434 0) (434 -65) (623.186 -410) (623.186 -420) (-623.186 -420) (-623.186 -410) (-434 -65))
   ("L" "BOCA-OCULTO" (-373 0) (-373 -65))
   ("L" "BOCA-OCULTO" (-173 0) (-173 -65))
   ("L" "BOCA-OCULTO" (-100 0) (-100 -65))
   ("L" "BOCA-OCULTO" (100 0) (100 -65))
   ("L" "BOCA-OCULTO" (173 0) (173 -65))
   ("L" "BOCA-OCULTO" (373 0) (373 -65))
   ("L" "BOCA-EIXO" (0 60) (0 -105))))
  (list "BTTC 2,50 - EXTRAPOLADO" "BNAA_BTTC250_PL"
   '(("P" "BOCA-CONCRETO" (-521 0) (521 0) (521 -85) (-521 -85))
   ("P" "BOCA-CONCRETO" (-521 -85) (-772.147 -520) (-743.28 -520) (-492.132 -85))
   ("P" "BOCA-CONCRETO" (521 -85) (772.147 -520) (743.28 -520) (492.132 -85))
   ("P" "BOCA-SOLEIRA" (-531 0) (531 0) (531 -85) (772.147 -520) (772.147 -530) (-772.147 -530) (-772.147 -520) (-531 -85))
   ("L" "BOCA-OCULTO" (-458 0) (-458 -85))
   ("L" "BOCA-OCULTO" (-208 0) (-208 -85))
   ("L" "BOCA-OCULTO" (-125 0) (-125 -85))
   ("L" "BOCA-OCULTO" (125 0) (125 -85))
   ("L" "BOCA-OCULTO" (208 0) (208 -85))
   ("L" "BOCA-OCULTO" (458 0) (458 -85))
   ("L" "BOCA-EIXO" (0 60) (0 -125))))
  (list "BTTC 3,00 - EXTRAPOLADO" "BNAA_BTTC300_PL"
   '(("P" "BOCA-CONCRETO" (-619 0) (619 0) (619 -100) (-619 -100))
   ("P" "BOCA-CONCRETO" (-619 -100) (-919.222 -620) (-884.581 -620) (-584.359 -100))
   ("P" "BOCA-CONCRETO" (619 -100) (919.222 -620) (884.581 -620) (584.359 -100))
   ("P" "BOCA-SOLEIRA" (-629 0) (629 0) (629 -100) (919.222 -620) (919.222 -630) (-919.222 -630) (-919.222 -620) (-629 -100))
   ("L" "BOCA-OCULTO" (-543 0) (-543 -100))
   ("L" "BOCA-OCULTO" (-243 0) (-243 -100))
   ("L" "BOCA-OCULTO" (-150 0) (-150 -100))
   ("L" "BOCA-OCULTO" (150 0) (150 -100))
   ("L" "BOCA-OCULTO" (243 0) (243 -100))
   ("L" "BOCA-OCULTO" (543 0) (543 -100))
   ("L" "BOCA-EIXO" (0 60) (0 -140))))
 ))
 (list "BOCA_BNAA_FRONTAL" (list
  (list "BSTC 1,00 - BNAA 03" "BNAA_BSTC100_FR"
   '(("P" "BOCA-CONCRETO" (-85 0) (85 0) (85 142) (-85 142))
   ("E" "BOCA-CONCRETO" (0 50) 50 50)
   ("P" "BOCA-CONCRETO" (-85 0) (-85 142) (-180.263 25) (-180.263 0))
   ("L" "BOCA-CONCRETO" (-157.169 0) (-157.169 25))
   ("P" "BOCA-CONCRETO" (85 0) (85 142) (180.263 25) (180.263 0))
   ("L" "BOCA-CONCRETO" (157.169 0) (157.169 25))
   ("P" "BOCA-SOLEIRA" (-180.263 0) (180.263 0) (180.263 -65) (-180.263 -65))
   ("L" "BOCA-OCULTO" (-180.263 -25) (180.263 -25))
   ("P" "BOCA-SOLEIRA" (-180.263 -65) (180.263 -65) (180.263 -70) (-180.263 -70))))
  (list "BSTC 1,20 - BNAA 04" "BNAA_BSTC120_FR"
   '(("P" "BOCA-CONCRETO" (-100 0) (100 0) (100 163) (-100 163))
   ("E" "BOCA-CONCRETO" (0 60) 60 60)
   ("P" "BOCA-CONCRETO" (-100 0) (-100 163) (-203.923 30) (-203.923 0))
   ("L" "BOCA-CONCRETO" (-180.829 0) (-180.829 30))
   ("P" "BOCA-CONCRETO" (100 0) (100 163) (203.923 30) (203.923 0))
   ("L" "BOCA-CONCRETO" (180.829 0) (180.829 30))
   ("P" "BOCA-SOLEIRA" (-203.923 0) (203.923 0) (203.923 -65) (-203.923 -65))
   ("L" "BOCA-OCULTO" (-203.923 -25) (203.923 -25))
   ("P" "BOCA-SOLEIRA" (-203.923 -65) (203.923 -65) (203.923 -70) (-203.923 -70))))
  (list "BSTC 1,50 - BNAA 05" "BNAA_BSTC150_FR"
   '(("P" "BOCA-CONCRETO" (-122.5 0) (122.5 0) (122.5 194) (-122.5 194))
   ("E" "BOCA-CONCRETO" (-0.5 75) 75 75)
   ("P" "BOCA-CONCRETO" (-122.5 0) (-122.5 194) (-272.611 35) (-272.611 0))
   ("L" "BOCA-CONCRETO" (-249.517 0) (-249.517 35))
   ("P" "BOCA-CONCRETO" (122.5 0) (122.5 194) (272.611 35) (272.611 0))
   ("L" "BOCA-CONCRETO" (249.517 0) (249.517 35))
   ("P" "BOCA-SOLEIRA" (-272.611 0) (272.611 0) (272.611 -70) (-272.611 -70))
   ("L" "BOCA-OCULTO" (-272.611 -30) (272.611 -30))
   ("P" "BOCA-SOLEIRA" (-272.611 -70) (272.611 -70) (272.611 -75) (-272.611 -75))))
  (list "BSTC 2,00 - EXTRAPOLADO" "BNAA_BSTC200_FR"
   '(("P" "BOCA-CONCRETO" (-163 0) (163 0) (163 244) (-163 244))
   ("E" "BOCA-CONCRETO" (0 100) 100 100)
   ("P" "BOCA-CONCRETO" (-163 0) (-163 244) (-362.186 45) (-362.186 0))
   ("L" "BOCA-CONCRETO" (-333.318 0) (-333.318 45))
   ("P" "BOCA-CONCRETO" (163 0) (163 244) (362.186 45) (362.186 0))
   ("L" "BOCA-CONCRETO" (333.318 0) (333.318 45))
   ("P" "BOCA-SOLEIRA" (-362.186 0) (362.186 0) (362.186 -80) (-362.186 -80))
   ("L" "BOCA-OCULTO" (-362.186 -35) (362.186 -35))
   ("P" "BOCA-SOLEIRA" (-362.186 -80) (362.186 -80) (362.186 -85) (-362.186 -85))))
  (list "BSTC 2,50 - EXTRAPOLADO" "BNAA_BSTC250_FR"
   '(("P" "BOCA-CONCRETO" (-203 0) (203 0) (203 294) (-203 294))
   ("E" "BOCA-CONCRETO" (0 125) 125 125)
   ("P" "BOCA-CONCRETO" (-203 0) (-203 294) (-454.147 60) (-454.147 0))
   ("L" "BOCA-CONCRETO" (-425.28 0) (-425.28 60))
   ("P" "BOCA-CONCRETO" (203 0) (203 294) (454.147 60) (454.147 0))
   ("L" "BOCA-CONCRETO" (425.28 0) (425.28 60))
   ("P" "BOCA-SOLEIRA" (-454.147 0) (454.147 0) (454.147 -90) (-454.147 -90))
   ("L" "BOCA-OCULTO" (-454.147 -40) (454.147 -40))
   ("P" "BOCA-SOLEIRA" (-454.147 -90) (454.147 -90) (454.147 -95) (-454.147 -95))))
  (list "BSTC 3,00 - EXTRAPOLADO" "BNAA_BSTC300_FR"
   '(("P" "BOCA-CONCRETO" (-244 0) (244 0) (244 344) (-244 344))
   ("E" "BOCA-CONCRETO" (0 150) 150 150)
   ("P" "BOCA-CONCRETO" (-244 0) (-244 344) (-544.222 70) (-544.222 0))
   ("L" "BOCA-CONCRETO" (-509.581 0) (-509.581 70))
   ("P" "BOCA-CONCRETO" (244 0) (244 344) (544.222 70) (544.222 0))
   ("L" "BOCA-CONCRETO" (509.581 0) (509.581 70))
   ("P" "BOCA-SOLEIRA" (-544.222 0) (544.222 0) (544.222 -95) (-544.222 -95))
   ("L" "BOCA-OCULTO" (-544.222 -40) (544.222 -40))
   ("P" "BOCA-SOLEIRA" (-544.222 -95) (544.222 -95) (544.222 -100) (-544.222 -100))))
  (list "BDTC 1,00 - BNAA 06" "BNAA_BDTC100_FR"
   '(("P" "BOCA-CONCRETO" (-157.5 0) (157.5 0) (157.5 142) (-157.5 142))
   ("E" "BOCA-CONCRETO" (-76.5 50) 50 50)
   ("E" "BOCA-CONCRETO" (76.5 50) 50 50)
   ("P" "BOCA-CONCRETO" (-157.5 0) (-157.5 142) (-252.763 30) (-252.763 0))
   ("L" "BOCA-CONCRETO" (-229.669 0) (-229.669 30))
   ("P" "BOCA-CONCRETO" (157.5 0) (157.5 142) (252.763 30) (252.763 0))
   ("L" "BOCA-CONCRETO" (229.669 0) (229.669 30))
   ("P" "BOCA-SOLEIRA" (-252.763 0) (252.763 0) (252.763 -65) (-252.763 -65))
   ("L" "BOCA-OCULTO" (-252.763 -25) (252.763 -25))
   ("P" "BOCA-SOLEIRA" (-252.763 -65) (252.763 -65) (252.763 -70) (-252.763 -70))))
  (list "BDTC 1,20 - BNAA 07" "BNAA_BDTC120_FR"
   '(("P" "BOCA-CONCRETO" (-185 0) (185 0) (185 163) (-185 163))
   ("E" "BOCA-CONCRETO" (-89 60) 60 60)
   ("E" "BOCA-CONCRETO" (89 60) 60 60)
   ("P" "BOCA-CONCRETO" (-185 0) (-185 163) (-288.923 35) (-288.923 0))
   ("L" "BOCA-CONCRETO" (-265.829 0) (-265.829 35))
   ("P" "BOCA-CONCRETO" (185 0) (185 163) (288.923 35) (288.923 0))
   ("L" "BOCA-CONCRETO" (265.829 0) (265.829 35))
   ("P" "BOCA-SOLEIRA" (-288.923 0) (288.923 0) (288.923 -65) (-288.923 -65))
   ("L" "BOCA-OCULTO" (-288.923 -25) (288.923 -25))
   ("P" "BOCA-SOLEIRA" (-288.923 -65) (288.923 -65) (288.923 -70) (-288.923 -70))))
  (list "BDTC 1,50 - BNAA 08" "BNAA_BDTC150_FR"
   '(("P" "BOCA-CONCRETO" (-220 0) (220 0) (220 194) (-220 194))
   ("E" "BOCA-CONCRETO" (-106 75) 75 75)
   ("E" "BOCA-CONCRETO" (106 75) 75 75)
   ("P" "BOCA-CONCRETO" (-220 0) (-220 194) (-370.111 35) (-370.111 0))
   ("L" "BOCA-CONCRETO" (-347.017 0) (-347.017 35))
   ("P" "BOCA-CONCRETO" (220 0) (220 194) (370.111 35) (370.111 0))
   ("L" "BOCA-CONCRETO" (347.017 0) (347.017 35))
   ("P" "BOCA-SOLEIRA" (-370.111 0) (370.111 0) (370.111 -70) (-370.111 -70))
   ("L" "BOCA-OCULTO" (-370.111 -30) (370.111 -30))
   ("P" "BOCA-SOLEIRA" (-370.111 -70) (370.111 -70) (370.111 -75) (-370.111 -75))))
  (list "BDTC 2,00 - EXTRAPOLADO" "BNAA_BDTC200_FR"
   '(("P" "BOCA-CONCRETO" (-288.5 0) (288.5 0) (288.5 244) (-288.5 244))
   ("E" "BOCA-CONCRETO" (-136.5 100) 100 100)
   ("E" "BOCA-CONCRETO" (136.5 100) 100 100)
   ("P" "BOCA-CONCRETO" (-288.5 0) (-288.5 244) (-487.686 45) (-487.686 0))
   ("L" "BOCA-CONCRETO" (-458.818 0) (-458.818 45))
   ("P" "BOCA-CONCRETO" (288.5 0) (288.5 244) (487.686 45) (487.686 0))
   ("L" "BOCA-CONCRETO" (458.818 0) (458.818 45))
   ("P" "BOCA-SOLEIRA" (-487.686 0) (487.686 0) (487.686 -80) (-487.686 -80))
   ("L" "BOCA-OCULTO" (-487.686 -35) (487.686 -35))
   ("P" "BOCA-SOLEIRA" (-487.686 -80) (487.686 -80) (487.686 -85) (-487.686 -85))))
  (list "BDTC 2,50 - EXTRAPOLADO" "BNAA_BDTC250_FR"
   '(("P" "BOCA-CONCRETO" (-356.5 0) (356.5 0) (356.5 294) (-356.5 294))
   ("E" "BOCA-CONCRETO" (-166.5 125) 125 125)
   ("E" "BOCA-CONCRETO" (166.5 125) 125 125)
   ("P" "BOCA-CONCRETO" (-356.5 0) (-356.5 294) (-607.647 60) (-607.647 0))
   ("L" "BOCA-CONCRETO" (-578.78 0) (-578.78 60))
   ("P" "BOCA-CONCRETO" (356.5 0) (356.5 294) (607.647 60) (607.647 0))
   ("L" "BOCA-CONCRETO" (578.78 0) (578.78 60))
   ("P" "BOCA-SOLEIRA" (-607.647 0) (607.647 0) (607.647 -90) (-607.647 -90))
   ("L" "BOCA-OCULTO" (-607.647 -40) (607.647 -40))
   ("P" "BOCA-SOLEIRA" (-607.647 -90) (607.647 -90) (607.647 -95) (-607.647 -95))))
  (list "BDTC 3,00 - EXTRAPOLADO" "BNAA_BDTC300_FR"
   '(("P" "BOCA-CONCRETO" (-424.5 0) (424.5 0) (424.5 344) (-424.5 344))
   ("E" "BOCA-CONCRETO" (-196.5 150) 150 150)
   ("E" "BOCA-CONCRETO" (196.5 150) 150 150)
   ("P" "BOCA-CONCRETO" (-424.5 0) (-424.5 344) (-724.722 70) (-724.722 0))
   ("L" "BOCA-CONCRETO" (-690.081 0) (-690.081 70))
   ("P" "BOCA-CONCRETO" (424.5 0) (424.5 344) (724.722 70) (724.722 0))
   ("L" "BOCA-CONCRETO" (690.081 0) (690.081 70))
   ("P" "BOCA-SOLEIRA" (-724.722 0) (724.722 0) (724.722 -95) (-724.722 -95))
   ("L" "BOCA-OCULTO" (-724.722 -40) (724.722 -40))
   ("P" "BOCA-SOLEIRA" (-724.722 -95) (724.722 -95) (724.722 -100) (-724.722 -100))))
  (list "BTTC 1,00 - BNAA 09" "BNAA_BTTC100_FR"
   '(("P" "BOCA-CONCRETO" (-235 0) (235 0) (235 142) (-235 142))
   ("E" "BOCA-CONCRETO" (-153 50) 50 50)
   ("E" "BOCA-CONCRETO" (0 50) 50 50)
   ("E" "BOCA-CONCRETO" (153 50) 50 50)
   ("P" "BOCA-CONCRETO" (-235 0) (-235 142) (-330.263 35) (-330.263 0))
   ("L" "BOCA-CONCRETO" (-307.169 0) (-307.169 35))
   ("P" "BOCA-CONCRETO" (235 0) (235 142) (330.263 35) (330.263 0))
   ("L" "BOCA-CONCRETO" (307.169 0) (307.169 35))
   ("P" "BOCA-SOLEIRA" (-330.263 0) (330.263 0) (330.263 -65) (-330.263 -65))
   ("L" "BOCA-OCULTO" (-330.263 -25) (330.263 -25))
   ("P" "BOCA-SOLEIRA" (-330.263 -65) (330.263 -65) (330.263 -70) (-330.263 -70))))
  (list "BTTC 1,20 - BNAA 10" "BNAA_BTTC120_FR"
   '(("P" "BOCA-CONCRETO" (-270 0) (270 0) (270 163) (-270 163))
   ("E" "BOCA-CONCRETO" (-178 60) 60 60)
   ("E" "BOCA-CONCRETO" (0 60) 60 60)
   ("E" "BOCA-CONCRETO" (178 60) 60 60)
   ("P" "BOCA-CONCRETO" (-270 0) (-270 163) (-373.923 40) (-373.923 0))
   ("L" "BOCA-CONCRETO" (-350.829 0) (-350.829 40))
   ("P" "BOCA-CONCRETO" (270 0) (270 163) (373.923 40) (373.923 0))
   ("L" "BOCA-CONCRETO" (350.829 0) (350.829 40))
   ("P" "BOCA-SOLEIRA" (-373.923 0) (373.923 0) (373.923 -65) (-373.923 -65))
   ("L" "BOCA-OCULTO" (-373.923 -25) (373.923 -25))
   ("P" "BOCA-SOLEIRA" (-373.923 -65) (373.923 -65) (373.923 -70) (-373.923 -70))))
  (list "BTTC 1,50 - BNAA 11" "BNAA_BTTC150_FR"
   '(("P" "BOCA-CONCRETO" (-325 0) (325 0) (325 194) (-325 194))
   ("E" "BOCA-CONCRETO" (-212 75) 75 75)
   ("E" "BOCA-CONCRETO" (0 75) 75 75)
   ("E" "BOCA-CONCRETO" (212 75) 75 75)
   ("P" "BOCA-CONCRETO" (-325 0) (-325 194) (-475.111 40) (-475.111 0))
   ("L" "BOCA-CONCRETO" (-452.017 0) (-452.017 40))
   ("P" "BOCA-CONCRETO" (325 0) (325 194) (475.111 40) (475.111 0))
   ("L" "BOCA-CONCRETO" (452.017 0) (452.017 40))
   ("P" "BOCA-SOLEIRA" (-475.111 0) (475.111 0) (475.111 -70) (-475.111 -70))
   ("L" "BOCA-OCULTO" (-475.111 -30) (475.111 -30))
   ("P" "BOCA-SOLEIRA" (-475.111 -70) (475.111 -70) (475.111 -75) (-475.111 -75))))
  (list "BTTC 2,00 - EXTRAPOLADO" "BNAA_BTTC200_FR"
   '(("P" "BOCA-CONCRETO" (-424 0) (424 0) (424 244) (-424 244))
   ("E" "BOCA-CONCRETO" (-273 100) 100 100)
   ("E" "BOCA-CONCRETO" (0 100) 100 100)
   ("E" "BOCA-CONCRETO" (273 100) 100 100)
   ("P" "BOCA-CONCRETO" (-424 0) (-424 244) (-623.186 55) (-623.186 0))
   ("L" "BOCA-CONCRETO" (-594.318 0) (-594.318 55))
   ("P" "BOCA-CONCRETO" (424 0) (424 244) (623.186 55) (623.186 0))
   ("L" "BOCA-CONCRETO" (594.318 0) (594.318 55))
   ("P" "BOCA-SOLEIRA" (-623.186 0) (623.186 0) (623.186 -80) (-623.186 -80))
   ("L" "BOCA-OCULTO" (-623.186 -35) (623.186 -35))
   ("P" "BOCA-SOLEIRA" (-623.186 -80) (623.186 -80) (623.186 -85) (-623.186 -85))))
  (list "BTTC 2,50 - EXTRAPOLADO" "BNAA_BTTC250_FR"
   '(("P" "BOCA-CONCRETO" (-521 0) (521 0) (521 294) (-521 294))
   ("E" "BOCA-CONCRETO" (-333 125) 125 125)
   ("E" "BOCA-CONCRETO" (0 125) 125 125)
   ("E" "BOCA-CONCRETO" (333 125) 125 125)
   ("P" "BOCA-CONCRETO" (-521 0) (-521 294) (-772.147 65) (-772.147 0))
   ("L" "BOCA-CONCRETO" (-743.28 0) (-743.28 65))
   ("P" "BOCA-CONCRETO" (521 0) (521 294) (772.147 65) (772.147 0))
   ("L" "BOCA-CONCRETO" (743.28 0) (743.28 65))
   ("P" "BOCA-SOLEIRA" (-772.147 0) (772.147 0) (772.147 -90) (-772.147 -90))
   ("L" "BOCA-OCULTO" (-772.147 -40) (772.147 -40))
   ("P" "BOCA-SOLEIRA" (-772.147 -90) (772.147 -90) (772.147 -95) (-772.147 -95))))
  (list "BTTC 3,00 - EXTRAPOLADO" "BNAA_BTTC300_FR"
   '(("P" "BOCA-CONCRETO" (-619 0) (619 0) (619 344) (-619 344))
   ("E" "BOCA-CONCRETO" (-393 150) 150 150)
   ("E" "BOCA-CONCRETO" (0 150) 150 150)
   ("E" "BOCA-CONCRETO" (393 150) 150 150)
   ("P" "BOCA-CONCRETO" (-619 0) (-619 344) (-919.222 80) (-919.222 0))
   ("L" "BOCA-CONCRETO" (-884.581 0) (-884.581 80))
   ("P" "BOCA-CONCRETO" (619 0) (619 344) (919.222 80) (919.222 0))
   ("L" "BOCA-CONCRETO" (884.581 0) (884.581 80))
   ("P" "BOCA-SOLEIRA" (-919.222 0) (919.222 0) (919.222 -95) (-919.222 -95))
   ("L" "BOCA-OCULTO" (-919.222 -40) (919.222 -40))
   ("P" "BOCA-SOLEIRA" (-919.222 -95) (919.222 -95) (919.222 -100) (-919.222 -100))))
 ))
 (list "BOCA_BEAA15_PLANTA" (list
  (list "BSTC 1,00 - BEAA 03" "BEAA15_BSTC100_PL"
   '(("P" "BOCA-CONCRETO" (-83.553 -22.388) (90.314 24.2) (98.079 -4.778) (-75.788 -51.366))
   ("P" "BOCA-CONCRETO" (-75.788 -51.366) (-192.461 -253.449) (-165.14 -246.128) (-48.468 -44.045))
   ("P" "BOCA-CONCRETO" (98.079 -4.778) (183.489 -152.713) (163.489 -158.072) (78.079 -10.137))
   ("P" "BOCA-SOLEIRA" (-93.212 -24.976) (99.973 26.788) (107.738 -2.19) (183.489 -152.713) (186.077 -162.372) (-189.872 -263.108) (-192.461 -253.449) (-85.447 -53.954))
   ("L" "BOCA-OCULTO" (-49.745 -13.329) (-49.745 -44.387))
   ("L" "BOCA-OCULTO" (50.255 13.466) (50.255 -17.593))
   ("L" "BOCA-EIXO" (0 62.117) (0 -72.469))))
  (list "BSTC 1,20 - BEAA 04" "BEAA15_BSTC120_PL"
   '(("P" "BOCA-CONCRETO" (-98.524 -26.4) (104.32 27.952) (114.673 -10.685) (-88.172 -65.037))
   ("P" "BOCA-CONCRETO" (-88.172 -65.037) (-215.451 -285.491) (-188.13 -278.17) (-60.851 -57.716))
   ("P" "BOCA-CONCRETO" (114.673 -10.685) (207.848 -172.068) (187.848 -177.427) (94.673 -16.044))
   ("P" "BOCA-SOLEIRA" (-108.184 -28.988) (113.979 30.541) (124.332 -8.096) (207.848 -172.068) (210.436 -181.727) (-212.863 -295.15) (-215.451 -285.491) (-97.831 -67.625))
   ("L" "BOCA-OCULTO" (-59.887 -16.047) (-59.887 -57.458))
   ("L" "BOCA-OCULTO" (60.113 16.107) (60.113 -25.304))
   ("L" "BOCA-EIXO" (0 62.117) (0 -82.822))))
  (list "BSTC 1,50 - BEAA 05" "BEAA15_BSTC150_PL"
   '(("P" "BOCA-CONCRETO" (-118.326 -31.705) (127.985 34.294) (140.926 -14.003) (-105.385 -80.002))
   ("P" "BOCA-CONCRETO" (-105.385 -80.002) (-289.233 -398.435) (-261.912 -391.115) (-78.064 -72.681))
   ("P" "BOCA-CONCRETO" (140.926 -14.003) (275.512 -247.112) (255.512 -252.471) (120.926 -19.362))
   ("P" "BOCA-SOLEIRA" (-127.985 -34.294) (137.644 36.882) (150.585 -11.415) (275.512 -247.112) (278.1 -256.772) (-286.645 -408.095) (-289.233 -398.435) (-115.044 -82.59))
   ("L" "BOCA-OCULTO" (-74.859 -20.058) (-74.859 -71.822))
   ("L" "BOCA-OCULTO" (75.141 20.134) (75.141 -31.63))
   ("L" "BOCA-EIXO" (0 62.117) (0 -93.175))))
  (list "BSTC 2,00 - EXTRAPOLADO" "BEAA15_BSTC200_PL"
   '(("P" "BOCA-CONCRETO" (-157.929 -42.317) (170.486 45.682) (187.309 -17.104) (-141.106 -105.102))
   ("P" "BOCA-CONCRETO" (-141.106 -105.102) (-385.057 -527.639) (-350.907 -518.488) (-106.955 -95.951))
   ("P" "BOCA-CONCRETO" (187.309 -17.104) (365.894 -326.422) (340.894 -333.121) (162.309 -23.802))
   ("P" "BOCA-SOLEIRA" (-167.588 -44.905) (180.145 48.27) (196.968 -14.515) (365.894 -326.422) (368.482 -336.081) (-382.469 -537.298) (-385.057 -527.639) (-150.765 -107.69))
   ("L" "BOCA-OCULTO" (-99.973 -26.788) (-99.973 -94.081))
   ("L" "BOCA-OCULTO" (100.027 26.802) (100.027 -40.491))
   ("L" "BOCA-EIXO" (0 62.117) (0 -108.704))))
  (list "BSTC 2,50 - EXTRAPOLADO" "BEAA15_BSTC250_PL"
   '(("P" "BOCA-CONCRETO" (-197.532 -52.928) (213.953 57.328) (235.952 -24.775) (-175.532 -135.032))
   ("P" "BOCA-CONCRETO" (-175.532 -135.032) (-483.124 -667.796) (-448.973 -658.646) (-141.382 -125.882))
   ("P" "BOCA-CONCRETO" (235.952 -24.775) (461.125 -414.786) (436.125 -421.484) (210.952 -31.474))
   ("P" "BOCA-SOLEIRA" (-207.191 -55.517) (223.612 59.917) (245.611 -22.187) (461.125 -414.786) (463.713 -424.445) (-480.535 -677.455) (-483.124 -667.796) (-185.191 -137.62))
   ("L" "BOCA-OCULTO" (-125.087 -33.517) (-125.087 -121.516))
   ("L" "BOCA-OCULTO" (124.913 33.47) (124.913 -54.528))
   ("L" "BOCA-EIXO" (0 62.117) (0 -129.41))))
  (list "BSTC 3,00 - EXTRAPOLADO" "BEAA15_BSTC300_PL"
   '(("P" "BOCA-CONCRETO" (-237.135 -63.54) (256.453 68.716) (282.335 -27.876) (-211.253 -160.133))
   ("P" "BOCA-CONCRETO" (-211.253 -160.133) (-578.948 -797) (-537.968 -786.019) (-170.272 -149.152))
   ("P" "BOCA-CONCRETO" (282.335 -27.876) (551.507 -494.095) (521.507 -502.134) (252.335 -35.915))
   ("P" "BOCA-SOLEIRA" (-246.794 -66.128) (266.113 71.305) (291.994 -25.288) (551.507 -494.095) (554.095 -503.755) (-576.36 -806.659) (-578.948 -797) (-220.912 -162.721))
   ("L" "BOCA-OCULTO" (-150.201 -40.246) (-150.201 -143.774))
   ("L" "BOCA-OCULTO" (149.799 40.138) (149.799 -63.389))
   ("L" "BOCA-EIXO" (0 62.117) (0 -144.939))))
  (list "BDTC 1,00 - BEAA 06" "BEAA15_BDTC100_PL"
   '(("P" "BOCA-CONCRETO" (-160.344 -42.964) (168.071 45.035) (175.836 16.057) (-152.579 -71.942))
   ("P" "BOCA-CONCRETO" (-152.579 -71.942) (-269.252 -274.025) (-241.931 -266.704) (-125.259 -64.621))
   ("P" "BOCA-CONCRETO" (175.836 16.057) (261.246 -131.878) (241.246 -137.237) (155.836 10.698))
   ("P" "BOCA-SOLEIRA" (-170.003 -45.552) (177.73 47.623) (185.495 18.645) (261.246 -131.878) (263.834 -141.537) (-266.664 -283.684) (-269.252 -274.025) (-162.238 -74.53))
   ("L" "BOCA-OCULTO" (-126.536 -33.905) (-126.536 -64.964))
   ("L" "BOCA-OCULTO" (-26.536 -7.11) (-26.536 -38.169))
   ("L" "BOCA-OCULTO" (26.536 7.11) (26.536 -23.948))
   ("L" "BOCA-OCULTO" (126.536 33.905) (126.536 2.847))
   ("L" "BOCA-EIXO" (0 62.117) (0 -72.469))))
  (list "BDTC 1,20 - BEAA 07" "BEAA15_BDTC120_PL"
   '(("P" "BOCA-CONCRETO" (-187.873 -50.34) (188.838 50.599) (199.191 11.962) (-177.52 -88.977))
   ("P" "BOCA-CONCRETO" (-177.52 -88.977) (-304.799 -309.431) (-277.479 -302.111) (-150.199 -81.657))
   ("P" "BOCA-CONCRETO" (199.191 11.962) (292.366 -149.421) (272.366 -154.78) (179.191 6.603))
   ("P" "BOCA-SOLEIRA" (-197.532 -52.928) (198.498 53.187) (208.851 14.55) (292.366 -149.421) (294.954 -159.081) (-302.211 -319.091) (-304.799 -309.431) (-187.179 -91.566))
   ("L" "BOCA-OCULTO" (-149.236 -39.988) (-149.236 -81.399))
   ("L" "BOCA-OCULTO" (-29.236 -7.834) (-29.236 -49.245))
   ("L" "BOCA-OCULTO" (29.236 7.834) (29.236 -33.577))
   ("L" "BOCA-OCULTO" (149.236 39.988) (149.236 -1.424))
   ("L" "BOCA-EIXO" (0 62.117) (0 -82.822))))
  (list "BDTC 1,50 - BEAA 08" "BEAA15_BDTC150_PL"
   '(("P" "BOCA-CONCRETO" (-225.061 -60.305) (224.095 60.046) (237.036 11.75) (-212.12 -108.601))
   ("P" "BOCA-CONCRETO" (-212.12 -108.601) (-395.968 -427.035) (-368.647 -419.714) (-184.799 -101.281))
   ("P" "BOCA-CONCRETO" (237.036 11.75) (371.622 -221.36) (351.622 -226.719) (217.036 6.391))
   ("P" "BOCA-SOLEIRA" (-234.72 -62.893) (233.754 62.634) (246.695 14.338) (371.622 -221.36) (374.21 -231.019) (-393.379 -436.694) (-395.968 -427.035) (-221.779 -111.189))
   ("L" "BOCA-OCULTO" (-180.628 -48.399) (-180.628 -100.163))
   ("L" "BOCA-OCULTO" (-30.628 -8.207) (-30.628 -59.971))
   ("L" "BOCA-OCULTO" (30.628 8.207) (30.628 -43.557))
   ("L" "BOCA-OCULTO" (180.628 48.399) (180.628 -3.365))
   ("L" "BOCA-EIXO" (0 62.117) (0 -93.175))))
  (list "BDTC 2,00 - EXTRAPOLADO" "BEAA15_BDTC200_PL"
   '(("P" "BOCA-CONCRETO" (-295.573 -79.199) (294.607 78.94) (311.431 16.155) (-278.75 -141.984))
   ("P" "BOCA-CONCRETO" (-278.75 -141.984) (-522.702 -564.521) (-488.551 -555.37) (-244.599 -132.833))
   ("P" "BOCA-CONCRETO" (311.431 16.155) (490.016 -293.164) (465.016 -299.863) (286.431 9.456))
   ("P" "BOCA-SOLEIRA" (-305.233 -81.787) (304.267 81.528) (321.09 18.743) (490.016 -293.164) (492.604 -302.823) (-520.114 -574.18) (-522.702 -564.521) (-288.409 -144.572))   ("L" "BOCA-OCULTO" (-236.652 -63.411) (-236.652 -130.704))
   ("L" "BOCA-OCULTO" (-36.652 -9.821) (-36.652 -77.114))
   ("L" "BOCA-OCULTO" (36.652 9.821) (36.652 -57.472))
   ("L" "BOCA-OCULTO" (236.652 63.411) (236.652 -3.882))
   ("L" "BOCA-EIXO" (0 62.117) (0 -108.704))))
  (list "BDTC 2,50 - EXTRAPOLADO" "BEAA15_BDTC250_PL"
   '(("P" "BOCA-CONCRETO" (-366.086 -98.092) (364.154 97.575) (386.154 15.471) (-344.086 -180.196))
   ("P" "BOCA-CONCRETO" (-344.086 -180.196) (-651.678 -712.96) (-617.527 -703.809) (-309.936 -171.045))
   ("P" "BOCA-CONCRETO" (386.154 15.471) (611.326 -374.539) (586.326 -381.238) (361.154 8.772))
   ("P" "BOCA-SOLEIRA" (-375.745 -100.681) (373.813 100.163) (395.813 18.059) (611.326 -374.539) (613.914 -384.199) (-649.09 -722.619) (-651.678 -712.96) (-353.746 -182.784))
   ("L" "BOCA-OCULTO" (-291.71 -78.163) (-291.71 -166.162))
   ("L" "BOCA-OCULTO" (-41.71 -11.176) (-41.71 -99.175))
   ("L" "BOCA-OCULTO" (41.71 11.176) (41.71 -76.822))
   ("L" "BOCA-OCULTO" (291.71 78.163) (291.71 -9.835))
   ("L" "BOCA-EIXO" (0 62.117) (0 -129.41))))
  (list "BDTC 3,00 - EXTRAPOLADO" "BEAA15_BDTC300_PL"
   '(("P" "BOCA-CONCRETO" (-435.15 -116.598) (433.218 116.08) (459.1 19.488) (-409.268 -213.191))
   ("P" "BOCA-CONCRETO" (-409.268 -213.191) (-776.963 -850.058) (-735.982 -839.077) (-368.287 -202.21))
   ("P" "BOCA-CONCRETO" (459.1 19.488) (728.271 -446.731) (698.271 -454.77) (429.1 11.449))
   ("P" "BOCA-SOLEIRA" (-444.809 -119.186) (442.877 118.669) (468.759 22.076) (728.271 -446.731) (730.86 -456.391) (-774.375 -859.717) (-776.963 -850.058) (-418.927 -215.779))
   ("L" "BOCA-OCULTO" (-346.284 -92.787) (-346.284 -196.314))
   ("L" "BOCA-OCULTO" (-46.284 -12.402) (-46.284 -115.929))
   ("L" "BOCA-OCULTO" (46.284 12.402) (46.284 -91.126))
   ("L" "BOCA-OCULTO" (346.284 92.787) (346.284 -10.741))
   ("L" "BOCA-EIXO" (0 62.117) (0 -144.939))))
  (list "BTTC 1,00 - BEAA 09" "BEAA15_BTTC100_PL"
   '(("P" "BOCA-CONCRETO" (-236.652 -63.411) (241.481 64.705) (249.246 35.727) (-228.887 -92.388))
   ("P" "BOCA-CONCRETO" (-228.887 -92.388) (-345.56 -294.471) (-318.239 -287.151) (-201.567 -85.068))
   ("P" "BOCA-CONCRETO" (249.246 35.727) (334.656 -112.208) (314.656 -117.567) (229.246 30.368))
   ("P" "BOCA-SOLEIRA" (-246.311 -65.999) (251.141 67.293) (258.905 38.315) (334.656 -112.208) (337.245 -121.867) (-342.972 -304.131) (-345.56 -294.471) (-238.547 -94.977))
   ("L" "BOCA-OCULTO" (-202.844 -54.352) (-202.844 -85.41))
   ("L" "BOCA-OCULTO" (-102.844 -27.557) (-102.844 -58.615))
   ("L" "BOCA-OCULTO" (-50 -13.397) (-50 -44.456))
   ("L" "BOCA-OCULTO" (50 13.397) (50 -17.661))
   ("L" "BOCA-OCULTO" (102.844 27.557) (102.844 -3.501))
   ("L" "BOCA-OCULTO" (202.844 54.352) (202.844 23.294))
   ("L" "BOCA-EIXO" (0 62.117) (0 -72.469))))
  (list "BTTC 1,20 - BEAA 10" "BEAA15_BTTC120_PL"
   '(("P" "BOCA-CONCRETO" (-276.738 -74.152) (278.67 74.669) (289.022 36.032) (-266.385 -112.789))
   ("P" "BOCA-CONCRETO" (-266.385 -112.789) (-393.664 -333.243) (-366.344 -325.922) (-239.064 -105.468))
   ("P" "BOCA-CONCRETO" (289.022 36.032) (382.197 -125.351) (362.197 -130.71) (269.022 30.673))
   ("P" "BOCA-SOLEIRA" (-286.397 -76.74) (288.329 77.257) (298.682 38.62) (382.197 -125.351) (384.785 -135.011) (-391.076 -342.902) (-393.664 -333.243) (-276.044 -115.377))
   ("L" "BOCA-OCULTO" (-238.101 -63.799) (-238.101 -105.21))
   ("L" "BOCA-OCULTO" (-118.101 -31.645) (-118.101 -73.056))
   ("L" "BOCA-OCULTO" (-60 -16.077) (-60 -57.488))
   ("L" "BOCA-OCULTO" (60 16.077) (60 -25.334))
   ("L" "BOCA-OCULTO" (118.101 31.645) (118.101 -9.766))
   ("L" "BOCA-OCULTO" (238.101 63.799) (238.101 22.388))
   ("L" "BOCA-EIXO" (0 62.117) (0 -82.822))))
  (list "BTTC 1,50 - BEAA 11" "BEAA15_BTTC150_PL"
   '(("P" "BOCA-CONCRETO" (-330.347 -88.516) (331.313 88.775) (344.254 40.479) (-317.406 -136.812))
   ("P" "BOCA-CONCRETO" (-317.406 -136.812) (-501.253 -455.246) (-473.933 -447.926) (-290.085 -129.492))
   ("P" "BOCA-CONCRETO" (344.254 40.479) (478.839 -192.631) (458.839 -197.99) (324.254 35.12))
   ("P" "BOCA-SOLEIRA" (-340.006 -91.104) (340.972 91.363) (353.913 43.067) (478.839 -192.631) (481.428 -202.29) (-498.665 -464.905) (-501.253 -455.246) (-327.065 -139.401))
   ("L" "BOCA-OCULTO" (-286.88 -76.869) (-286.88 -128.633))
   ("L" "BOCA-OCULTO" (-136.88 -36.677) (-136.88 -88.441))
   ("L" "BOCA-OCULTO" (-75 -20.096) (-75 -71.86))
   ("L" "BOCA-OCULTO" (75 20.096) (75 -31.668))
   ("L" "BOCA-OCULTO" (136.88 36.677) (136.88 -15.087))
   ("L" "BOCA-OCULTO" (286.88 76.869) (286.88 25.105))
   ("L" "BOCA-EIXO" (0 62.117) (0 -93.175))))
  (list "BTTC 2,00 - EXTRAPOLADO" "BEAA15_BTTC200_PL"
   '(("P" "BOCA-CONCRETO" (-430.803 -115.433) (431.769 115.692) (448.592 52.907) (-413.98 -178.218))
   ("P" "BOCA-CONCRETO" (-413.98 -178.218) (-657.932 -600.755) (-623.781 -591.605) (-379.829 -169.068))
   ("P" "BOCA-CONCRETO" (448.592 52.907) (627.177 -256.412) (602.177 -263.11) (423.592 46.208))
   ("P" "BOCA-SOLEIRA" (-440.462 -118.021) (441.428 118.28) (458.251 55.495) (627.177 -256.412) (629.765 -266.071) (-655.343 -610.415) (-657.932 -600.755) (-423.639 -180.807))
   ("L" "BOCA-OCULTO" (-372.847 -99.904) (-372.847 -167.197))
   ("L" "BOCA-OCULTO" (-172.847 -46.314) (-172.847 -113.607))
   ("L" "BOCA-OCULTO" (-100 -26.795) (-100 -94.088))
   ("L" "BOCA-OCULTO" (100 26.795) (100 -40.498))
   ("L" "BOCA-OCULTO" (172.847 46.314) (172.847 -20.979))
   ("L" "BOCA-OCULTO" (372.847 99.904) (372.847 32.611))
   ("L" "BOCA-EIXO" (0 62.117) (0 -108.704))))
  (list "BTTC 2,50 - EXTRAPOLADO" "BEAA15_BTTC250_PL"
   '(("P" "BOCA-CONCRETO" (-530.293 -142.092) (532.225 142.609) (554.225 60.506) (-508.294 -224.195))
   ("P" "BOCA-CONCRETO" (-508.294 -224.195) (-815.885 -756.959) (-781.734 -747.809) (-474.143 -215.045))
   ("P" "BOCA-CONCRETO" (554.225 60.506) (779.397 -329.505) (754.397 -336.203) (529.225 53.807))
   ("P" "BOCA-SOLEIRA" (-539.953 -144.68) (541.884 145.197) (563.884 63.094) (779.397 -329.505) (781.986 -339.164) (-813.297 -766.619) (-815.885 -756.959) (-517.953 -226.784))
   ("L" "BOCA-OCULTO" (-457.849 -122.68) (-457.849 -210.679))
   ("L" "BOCA-OCULTO" (-207.849 -55.693) (-207.849 -143.691))
   ("L" "BOCA-OCULTO" (-125 -33.494) (-125 -121.492))
   ("L" "BOCA-OCULTO" (125 33.494) (125 -54.505))
   ("L" "BOCA-OCULTO" (207.849 55.693) (207.849 -32.306))
   ("L" "BOCA-OCULTO" (457.849 122.68) (457.849 34.682))
   ("L" "BOCA-EIXO" (0 62.117) (0 -129.41))))
  (list "BTTC 3,00 - EXTRAPOLADO" "BEAA15_BTTC300_PL"
   '(("P" "BOCA-CONCRETO" (-629.784 -168.75) (631.715 169.268) (657.597 72.675) (-603.902 -265.343))
   ("P" "BOCA-CONCRETO" (-603.902 -265.343) (-971.597 -902.21) (-930.616 -891.229) (-562.921 -254.362))
   ("P" "BOCA-CONCRETO" (657.597 72.675) (926.769 -393.544) (896.769 -401.583) (627.597 64.637))
   ("P" "BOCA-SOLEIRA" (-639.443 -171.338) (641.375 171.856) (667.257 75.263) (926.769 -393.544) (929.357 -403.203) (-969.009 -911.869) (-971.597 -902.21) (-613.561 -267.931))
   ("L" "BOCA-OCULTO" (-542.85 -145.456) (-542.85 -248.984))
   ("L" "BOCA-OCULTO" (-242.85 -65.072) (-242.85 -168.599))
   ("L" "BOCA-OCULTO" (-150 -40.192) (-150 -143.72))
   ("L" "BOCA-OCULTO" (150 40.192) (150 -63.335))
   ("L" "BOCA-OCULTO" (242.85 65.072) (242.85 -38.456))
   ("L" "BOCA-OCULTO" (542.85 145.456) (542.85 41.929))
   ("L" "BOCA-EIXO" (0 62.117) (0 -144.939))))
 ))
 (list "BOCA_BEAA15_FRONTAL" (list
  (list "BSTC 1,00 - BEAA 03" "BEAA15_BSTC100_FR"
   '(("P" "BOCA-CONCRETO" (-78.462 0) (101.538 0) (101.538 142) (-78.462 142))
   ("E" "BOCA-CONCRETO" (0.264 50) 51.764 50)
   ("P" "BOCA-CONCRETO" (-78.462 0) (-78.462 142) (-243.462 25) (-243.462 0))
   ("L" "BOCA-CONCRETO" (-215.177 0) (-215.177 25))
   ("P" "BOCA-CONCRETO" (101.538 0) (101.538 142) (145.75 25) (145.75 0))
   ("L" "BOCA-CONCRETO" (125.045 0) (125.045 25))
   ("P" "BOCA-SOLEIRA" (-243.462 0) (145.75 0) (145.75 -65) (-243.462 -65))
   ("L" "BOCA-OCULTO" (-243.462 -25) (145.75 -25))
   ("P" "BOCA-SOLEIRA" (-243.462 -65) (145.75 -65) (145.75 -70) (-243.462 -70))))
  (list "BSTC 1,20 - BEAA 04" "BEAA15_BSTC120_FR"
   '(("P" "BOCA-CONCRETO" (-91.282 0) (118.718 0) (118.718 163) (-91.282 163))
   ("E" "BOCA-CONCRETO" (0.117 60) 62.117 60)
   ("P" "BOCA-CONCRETO" (-91.282 0) (-91.282 163) (-271.282 30) (-271.282 0))
   ("L" "BOCA-CONCRETO" (-242.998 0) (-242.998 30))
   ("P" "BOCA-CONCRETO" (118.718 0) (118.718 163) (166.949 30) (166.949 0))
   ("L" "BOCA-CONCRETO" (146.243 0) (146.243 30))
   ("P" "BOCA-SOLEIRA" (-271.282 0) (166.949 0) (166.949 -65) (-271.282 -65))
   ("L" "BOCA-OCULTO" (-271.282 -25) (166.949 -25))
   ("P" "BOCA-SOLEIRA" (-271.282 -65) (166.949 -65) (166.949 -70) (-271.282 -70))))
  (list "BSTC 1,50 - BEAA 05" "BEAA15_BSTC150_FR"
   '(("P" "BOCA-CONCRETO" (-109.103 0) (145.897 0) (145.897 194) (-109.103 194))
   ("E" "BOCA-CONCRETO" (0.146 75) 77.646 75)
   ("P" "BOCA-CONCRETO" (-109.103 0) (-109.103 194) (-369.103 35) (-369.103 0))
   ("L" "BOCA-CONCRETO" (-340.818 0) (-340.818 35))
   ("P" "BOCA-CONCRETO" (145.897 0) (145.897 194) (215.564 35) (215.564 0))
   ("L" "BOCA-CONCRETO" (194.859 0) (194.859 35))
   ("P" "BOCA-SOLEIRA" (-369.103 0) (215.564 0) (215.564 -70) (-369.103 -70))
   ("L" "BOCA-OCULTO" (-369.103 -30) (215.564 -30))
   ("P" "BOCA-SOLEIRA" (-369.103 -70) (215.564 -70) (215.564 -75) (-369.103 -75))))
  (list "BSTC 2,00 - EXTRAPOLADO" "BEAA15_BSTC200_FR"
   '(("P" "BOCA-CONCRETO" (-146.083 0) (193.917 0) (193.917 244) (-146.083 244))
   ("E" "BOCA-CONCRETO" (0.028 100) 103.528 100)
   ("P" "BOCA-CONCRETO" (-146.083 0) (-146.083 244) (-491.083 45) (-491.083 0))
   ("L" "BOCA-CONCRETO" (-455.728 0) (-455.728 45))
   ("P" "BOCA-CONCRETO" (193.917 0) (193.917 244) (286.359 45) (286.359 0))
   ("L" "BOCA-CONCRETO" (260.477 0) (260.477 45))
   ("P" "BOCA-SOLEIRA" (-491.083 0) (286.359 0) (286.359 -80) (-491.083 -80))
   ("L" "BOCA-OCULTO" (-491.083 -35) (286.359 -35))
   ("P" "BOCA-SOLEIRA" (-491.083 -80) (286.359 -80) (286.359 -85) (-491.083 -85))))
  (list "BSTC 2,50 - EXTRAPOLADO" "BEAA15_BSTC250_FR"
   '(("P" "BOCA-CONCRETO" (-181.724 0) (244.276 0) (244.276 294) (-181.724 294))
   ("E" "BOCA-CONCRETO" (-0.09 125) 129.41 125)
   ("P" "BOCA-CONCRETO" (-181.724 0) (-181.724 294) (-616.724 60) (-616.724 0))
   ("L" "BOCA-CONCRETO" (-581.369 0) (-581.369 60))
   ("P" "BOCA-CONCRETO" (244.276 0) (244.276 294) (360.834 60) (360.834 0))
   ("L" "BOCA-CONCRETO" (334.952 0) (334.952 60))
   ("P" "BOCA-SOLEIRA" (-616.724 0) (360.834 0) (360.834 -90) (-616.724 -90))
   ("L" "BOCA-OCULTO" (-616.724 -40) (360.834 -40))
   ("P" "BOCA-SOLEIRA" (-616.724 -90) (360.834 -90) (360.834 -95) (-616.724 -95))))
  (list "BSTC 3,00 - EXTRAPOLADO" "BEAA15_BSTC300_FR"
   '(("P" "BOCA-CONCRETO" (-218.705 0) (292.295 0) (292.295 344) (-218.705 344))
   ("E" "BOCA-CONCRETO" (-0.209 150) 155.291 150)
   ("P" "BOCA-CONCRETO" (-218.705 0) (-218.705 344) (-738.705 70) (-738.705 0))
   ("L" "BOCA-CONCRETO" (-696.279 0) (-696.279 70))
   ("P" "BOCA-CONCRETO" (292.295 0) (292.295 344) (431.628 70) (431.628 0))
   ("L" "BOCA-CONCRETO" (400.57 0) (400.57 70))
   ("P" "BOCA-SOLEIRA" (-738.705 0) (431.628 0) (431.628 -95) (-738.705 -95))
   ("L" "BOCA-OCULTO" (-738.705 -40) (431.628 -40))
   ("P" "BOCA-SOLEIRA" (-738.705 -95) (431.628 -95) (431.628 -100) (-738.705 -100))))
  (list "BDTC 1,00 - BEAA 06" "BEAA15_BDTC100_FR"
   '(("P" "BOCA-CONCRETO" (-157.962 0) (182.038 0) (182.038 142) (-157.962 142))
   ("E" "BOCA-CONCRETO" (-79.236 50) 51.764 50)
   ("E" "BOCA-CONCRETO" (79.236 50) 51.764 50)
   ("P" "BOCA-CONCRETO" (-157.962 0) (-157.962 142) (-322.962 30) (-322.962 0))
   ("L" "BOCA-CONCRETO" (-294.677 0) (-294.677 30))
   ("P" "BOCA-CONCRETO" (182.038 0) (182.038 142) (226.25 30) (226.25 0))
   ("L" "BOCA-CONCRETO" (205.545 0) (205.545 30))
   ("P" "BOCA-SOLEIRA" (-322.962 0) (226.25 0) (226.25 -65) (-322.962 -65))
   ("L" "BOCA-OCULTO" (-322.962 -25) (226.25 -25))
   ("P" "BOCA-SOLEIRA" (-322.962 -65) (226.25 -65) (226.25 -70) (-322.962 -70))))
  (list "BDTC 1,20 - BEAA 07" "BEAA15_BDTC120_FR"
   '(("P" "BOCA-CONCRETO" (-183.782 0) (206.218 0) (206.218 163) (-183.782 163))
   ("E" "BOCA-CONCRETO" (-92.383 60) 62.117 60)
   ("E" "BOCA-CONCRETO" (92.383 60) 62.117 60)
   ("P" "BOCA-CONCRETO" (-183.782 0) (-183.782 163) (-363.782 35) (-363.782 0))
   ("L" "BOCA-CONCRETO" (-335.498 0) (-335.498 35))
   ("P" "BOCA-CONCRETO" (206.218 0) (206.218 163) (254.449 35) (254.449 0))
   ("L" "BOCA-CONCRETO" (233.743 0) (233.743 35))
   ("P" "BOCA-SOLEIRA" (-363.782 0) (254.449 0) (254.449 -65) (-363.782 -65))
   ("L" "BOCA-OCULTO" (-363.782 -25) (254.449 -25))
   ("P" "BOCA-SOLEIRA" (-363.782 -65) (254.449 -65) (254.449 -70) (-363.782 -70))))
  (list "BDTC 1,50 - BEAA 08" "BEAA15_BDTC150_FR"
   '(("P" "BOCA-CONCRETO" (-219.603 0) (245.397 0) (245.397 194) (-219.603 194))
   ("E" "BOCA-CONCRETO" (-109.354 75) 77.646 75)
   ("E" "BOCA-CONCRETO" (109.354 75) 77.646 75)
   ("P" "BOCA-CONCRETO" (-219.603 0) (-219.603 194) (-479.603 35) (-479.603 0))
   ("L" "BOCA-CONCRETO" (-451.318 0) (-451.318 35))
   ("P" "BOCA-CONCRETO" (245.397 0) (245.397 194) (315.064 35) (315.064 0))
   ("L" "BOCA-CONCRETO" (294.359 0) (294.359 35))
   ("P" "BOCA-SOLEIRA" (-479.603 0) (315.064 0) (315.064 -70) (-479.603 -70))
   ("L" "BOCA-OCULTO" (-479.603 -30) (315.064 -30))
   ("P" "BOCA-SOLEIRA" (-479.603 -70) (315.064 -70) (315.064 -75) (-479.603 -75))))
  (list "BDTC 2,00 - EXTRAPOLADO" "BEAA15_BDTC200_FR"
   '(("P" "BOCA-CONCRETO" (-288.583 0) (322.417 0) (322.417 244) (-288.583 244))
   ("E" "BOCA-CONCRETO" (-141.472 100) 103.528 100)
   ("E" "BOCA-CONCRETO" (141.472 100) 103.528 100)
   ("P" "BOCA-CONCRETO" (-288.583 0) (-288.583 244) (-633.583 45) (-633.583 0))
   ("L" "BOCA-CONCRETO" (-598.228 0) (-598.228 45))
   ("P" "BOCA-CONCRETO" (322.417 0) (322.417 244) (414.859 45) (414.859 0))
   ("L" "BOCA-CONCRETO" (388.977 0) (388.977 45))
   ("P" "BOCA-SOLEIRA" (-633.583 0) (414.859 0) (414.859 -80) (-633.583 -80))
   ("L" "BOCA-OCULTO" (-633.583 -35) (414.859 -35))
   ("P" "BOCA-SOLEIRA" (-633.583 -80) (414.859 -80) (414.859 -85) (-633.583 -85))))
  (list "BDTC 2,50 - EXTRAPOLADO" "BEAA15_BDTC250_FR"
   '(("P" "BOCA-CONCRETO" (-356.224 0) (399.776 0) (399.776 294) (-356.224 294))
   ("E" "BOCA-CONCRETO" (-172.59 125) 129.41 125)
   ("E" "BOCA-CONCRETO" (172.59 125) 129.41 125)
   ("P" "BOCA-CONCRETO" (-356.224 0) (-356.224 294) (-791.224 60) (-791.224 0))
   ("L" "BOCA-CONCRETO" (-755.869 0) (-755.869 60))
   ("P" "BOCA-CONCRETO" (399.776 0) (399.776 294) (516.334 60) (516.334 0))
   ("L" "BOCA-CONCRETO" (490.452 0) (490.452 60))
   ("P" "BOCA-SOLEIRA" (-791.224 0) (516.334 0) (516.334 -90) (-791.224 -90))
   ("L" "BOCA-OCULTO" (-791.224 -40) (516.334 -40))
   ("P" "BOCA-SOLEIRA" (-791.224 -90) (516.334 -90) (516.334 -95) (-791.224 -95))))
  (list "BDTC 3,00 - EXTRAPOLADO" "BEAA15_BDTC300_FR"
   '(("P" "BOCA-CONCRETO" (-423.705 0) (475.295 0) (475.295 344) (-423.705 344))
   ("E" "BOCA-CONCRETO" (-203.209 150) 155.291 150)
   ("E" "BOCA-CONCRETO" (203.209 150) 155.291 150)
   ("P" "BOCA-CONCRETO" (-423.705 0) (-423.705 344) (-943.705 70) (-943.705 0))
   ("L" "BOCA-CONCRETO" (-901.279 0) (-901.279 70))
   ("P" "BOCA-CONCRETO" (475.295 0) (475.295 344) (614.628 70) (614.628 0))
   ("L" "BOCA-CONCRETO" (583.57 0) (583.57 70))
   ("P" "BOCA-SOLEIRA" (-943.705 0) (614.628 0) (614.628 -95) (-943.705 -95))
   ("L" "BOCA-OCULTO" (-943.705 -40) (614.628 -40))
   ("P" "BOCA-SOLEIRA" (-943.705 -95) (614.628 -95) (614.628 -100) (-943.705 -100))))
  (list "BTTC 1,00 - BEAA 09" "BEAA15_BTTC100_FR"
   '(("P" "BOCA-CONCRETO" (-236.962 0) (258.038 0) (258.038 142) (-236.962 142))
   ("E" "BOCA-CONCRETO" (-158.236 50) 51.764 50)
   ("E" "BOCA-CONCRETO" (0 50) 51.764 50)
   ("E" "BOCA-CONCRETO" (158.236 50) 51.764 50)
   ("P" "BOCA-CONCRETO" (-236.962 0) (-236.962 142) (-401.962 35) (-401.962 0))
   ("L" "BOCA-CONCRETO" (-373.677 0) (-373.677 35))
   ("P" "BOCA-CONCRETO" (258.038 0) (258.038 142) (302.25 35) (302.25 0))
   ("L" "BOCA-CONCRETO" (281.545 0) (281.545 35))
   ("P" "BOCA-SOLEIRA" (-401.962 0) (302.25 0) (302.25 -65) (-401.962 -65))
   ("L" "BOCA-OCULTO" (-401.962 -25) (302.25 -25))
   ("P" "BOCA-SOLEIRA" (-401.962 -65) (302.25 -65) (302.25 -70) (-401.962 -70))))
  (list "BTTC 1,20 - BEAA 10" "BEAA15_BTTC120_FR"
   '(("P" "BOCA-CONCRETO" (-275.782 0) (299.218 0) (299.218 163) (-275.782 163))
   ("E" "BOCA-CONCRETO" (-184.383 60) 62.117 60)
   ("E" "BOCA-CONCRETO" (0 60) 62.117 60)
   ("E" "BOCA-CONCRETO" (184.383 60) 62.117 60)
   ("P" "BOCA-CONCRETO" (-275.782 0) (-275.782 163) (-455.782 40) (-455.782 0))
   ("L" "BOCA-CONCRETO" (-427.498 0) (-427.498 40))
   ("P" "BOCA-CONCRETO" (299.218 0) (299.218 163) (347.449 40) (347.449 0))
   ("L" "BOCA-CONCRETO" (326.743 0) (326.743 40))
   ("P" "BOCA-SOLEIRA" (-455.782 0) (347.449 0) (347.449 -65) (-455.782 -65))
   ("L" "BOCA-OCULTO" (-455.782 -25) (347.449 -25))
   ("P" "BOCA-SOLEIRA" (-455.782 -65) (347.449 -65) (347.449 -70) (-455.782 -70))))
  (list "BTTC 1,50 - BEAA 11" "BEAA15_BTTC150_FR"
   '(("P" "BOCA-CONCRETO" (-328.603 0) (356.397 0) (356.397 194) (-328.603 194))
   ("E" "BOCA-CONCRETO" (-219.354 75) 77.646 75)
   ("E" "BOCA-CONCRETO" (0 75) 77.646 75)
   ("E" "BOCA-CONCRETO" (219.354 75) 77.646 75)
   ("P" "BOCA-CONCRETO" (-328.603 0) (-328.603 194) (-588.603 40) (-588.603 0))
   ("L" "BOCA-CONCRETO" (-560.318 0) (-560.318 40))
   ("P" "BOCA-CONCRETO" (356.397 0) (356.397 194) (426.064 40) (426.064 0))
   ("L" "BOCA-CONCRETO" (405.359 0) (405.359 40))
   ("P" "BOCA-SOLEIRA" (-588.603 0) (426.064 0) (426.064 -70) (-588.603 -70))
   ("L" "BOCA-OCULTO" (-588.603 -30) (426.064 -30))
   ("P" "BOCA-SOLEIRA" (-588.603 -70) (426.064 -70) (426.064 -75) (-588.603 -75))))
  (list "BTTC 2,00 - EXTRAPOLADO" "BEAA15_BTTC200_FR"
   '(("P" "BOCA-CONCRETO" (-428.583 0) (464.417 0) (464.417 244) (-428.583 244))
   ("E" "BOCA-CONCRETO" (-282.472 100) 103.528 100)
   ("E" "BOCA-CONCRETO" (0 100) 103.528 100)
   ("E" "BOCA-CONCRETO" (282.472 100) 103.528 100)
   ("P" "BOCA-CONCRETO" (-428.583 0) (-428.583 244) (-773.583 55) (-773.583 0))
   ("L" "BOCA-CONCRETO" (-738.228 0) (-738.228 55))
   ("P" "BOCA-CONCRETO" (464.417 0) (464.417 244) (556.859 55) (556.859 0))
   ("L" "BOCA-CONCRETO" (530.977 0) (530.977 55))
   ("P" "BOCA-SOLEIRA" (-773.583 0) (556.859 0) (556.859 -80) (-773.583 -80))
   ("L" "BOCA-OCULTO" (-773.583 -35) (556.859 -35))
   ("P" "BOCA-SOLEIRA" (-773.583 -80) (556.859 -80) (556.859 -85) (-773.583 -85))))
  (list "BTTC 2,50 - EXTRAPOLADO" "BEAA15_BTTC250_FR"
   '(("P" "BOCA-CONCRETO" (-526.224 0) (573.776 0) (573.776 294) (-526.224 294))
   ("E" "BOCA-CONCRETO" (-344.59 125) 129.41 125)
   ("E" "BOCA-CONCRETO" (0 125) 129.41 125)
   ("E" "BOCA-CONCRETO" (344.59 125) 129.41 125)
   ("P" "BOCA-CONCRETO" (-526.224 0) (-526.224 294) (-961.224 65) (-961.224 0))
   ("L" "BOCA-CONCRETO" (-925.869 0) (-925.869 65))
   ("P" "BOCA-CONCRETO" (573.776 0) (573.776 294) (690.334 65) (690.334 0))
   ("L" "BOCA-CONCRETO" (664.452 0) (664.452 65))
   ("P" "BOCA-SOLEIRA" (-961.224 0) (690.334 0) (690.334 -90) (-961.224 -90))
   ("L" "BOCA-OCULTO" (-961.224 -40) (690.334 -40))
   ("P" "BOCA-SOLEIRA" (-961.224 -90) (690.334 -90) (690.334 -95) (-961.224 -95))))
  (list "BTTC 3,00 - EXTRAPOLADO" "BEAA15_BTTC300_FR"
   '(("P" "BOCA-CONCRETO" (-625.205 0) (680.795 0) (680.795 344) (-625.205 344))
   ("E" "BOCA-CONCRETO" (-406.709 150) 155.291 150)
   ("E" "BOCA-CONCRETO" (0 150) 155.291 150)
   ("E" "BOCA-CONCRETO" (406.709 150) 155.291 150)
   ("P" "BOCA-CONCRETO" (-625.205 0) (-625.205 344) (-1145.205 80) (-1145.205 0))
   ("L" "BOCA-CONCRETO" (-1102.779 0) (-1102.779 80))
   ("P" "BOCA-CONCRETO" (680.795 0) (680.795 344) (820.128 80) (820.128 0))
   ("L" "BOCA-CONCRETO" (789.07 0) (789.07 80))
   ("P" "BOCA-SOLEIRA" (-1145.205 0) (820.128 0) (820.128 -95) (-1145.205 -95))
   ("L" "BOCA-OCULTO" (-1145.205 -40) (820.128 -40))
   ("P" "BOCA-SOLEIRA" (-1145.205 -95) (820.128 -95) (820.128 -100) (-1145.205 -100))))
 ))
 (list "BOCA_BEAA30_PLANTA" (list
  (list "BSTC 1,00 - BEAA 14" "BEAA30_BSTC100_PL"
   '(("P" "BOCA-CONCRETO" (-89.634 -51.75) (92.232 53.25) (107.232 27.269) (-74.634 -77.731))
   ("P" "BOCA-CONCRETO" (-74.634 -77.731) (-196.208 -338.447) (-166.01 -321.013) (-44.436 -60.296))
   ("P" "BOCA-CONCRETO" (107.232 27.269) (189.732 -115.625) (172.411 -125.625) (89.911 17.269))
   ("P" "BOCA-SOLEIRA" (-98.294 -56.75) (100.892 58.25) (115.892 32.269) (189.732 -115.625) (194.732 -124.285) (-191.208 -347.107) (-196.208 -338.447) (-83.294 -82.731))
   ("L" "BOCA-OCULTO" (-49.796 -28.75) (-49.796 -63.391))
   ("L" "BOCA-OCULTO" (50.204 28.985) (50.204 -5.656))
   ("L" "BOCA-EIXO" (0 69.282) (0 -80.829))))
  (list "BSTC 1,20 - BEAA 15" "BEAA30_BSTC120_PL"
   '(("P" "BOCA-CONCRETO" (-106.954 -61.75) (105.222 60.75) (125.222 26.109) (-86.954 -96.391))
   ("P" "BOCA-CONCRETO" (-86.954 -96.391) (-219.58 -380.809) (-189.383 -363.374) (-56.757 -78.957))
   ("P" "BOCA-CONCRETO" (125.222 26.109) (215.222 -129.776) (197.902 -139.776) (107.902 16.109))
   ("P" "BOCA-SOLEIRA" (-115.614 -66.75) (113.882 65.75) (133.882 31.109) (215.222 -129.776) (220.222 -138.436) (-214.58 -389.469) (-219.58 -380.809) (-95.614 -101.391))
   ("L" "BOCA-OCULTO" (-60.189 -34.75) (-60.189 -80.938))
   ("L" "BOCA-OCULTO" (59.811 34.532) (59.811 -11.656))
   ("L" "BOCA-EIXO" (0 69.282) (0 -92.376))))
  (list "BSTC 1,50 - BEAA 16" "BEAA30_BSTC150_PL"
   '(("P" "BOCA-CONCRETO" (-129.038 -74.5) (126.44 73) (151.44 29.699) (-104.038 -117.801))
   ("P" "BOCA-CONCRETO" (-104.038 -117.801) (-295.609 -528.627) (-265.412 -511.193) (-73.84 -100.367))
   ("P" "BOCA-CONCRETO" (151.44 29.699) (281.44 -195.468) (264.119 -205.468) (134.119 19.699))
   ("P" "BOCA-SOLEIRA" (-137.698 -79.5) (135.1 78) (160.1 34.699) (281.44 -195.468) (286.44 -204.128) (-290.609 -537.287) (-295.609 -528.627) (-112.698 -122.801))
   ("L" "BOCA-OCULTO" (-75.344 -43.5) (-75.344 -101.235))
   ("L" "BOCA-OCULTO" (74.656 43.103) (74.656 -14.632))
   ("L" "BOCA-EIXO" (0 69.282) (0 -103.923))))
  (list "BSTC 2,00 - EXTRAPOLADO" "BEAA30_BSTC200_PL"
   '(("P" "BOCA-CONCRETO" (-171.906 -99.25) (168.442 97.25) (200.942 40.958) (-139.406 -155.542))
   ("P" "BOCA-CONCRETO" (-139.406 -155.542) (-393.606 -700.676) (-355.86 -678.883) (-101.659 -133.749))
   ("P" "BOCA-CONCRETO" (200.942 40.958) (373.442 -257.82) (351.791 -270.32) (179.291 28.458))
   ("P" "BOCA-SOLEIRA" (-180.566 -104.25) (177.102 102.25) (209.602 45.958) (373.442 -257.82) (378.442 -266.481) (-388.606 -709.336) (-393.606 -700.676) (-148.066 -160.542))
   ("L" "BOCA-OCULTO" (-100.026 -57.75) (-100.026 -132.806))
   ("L" "BOCA-OCULTO" (99.974 57.72) (99.974 -17.335))
   ("L" "BOCA-EIXO" (0 69.282) (0 -121.244))))
  (list "BSTC 2,50 - EXTRAPOLADO" "BEAA30_BSTC250_PL"
   '(("P" "BOCA-CONCRETO" (-214.341 -123.75) (210.011 121.25) (252.511 47.638) (-171.841 -197.362))
   ("P" "BOCA-CONCRETO" (-171.841 -197.362) (-492.355 -884.705) (-454.608 -862.912) (-134.095 -175.569))
   ("P" "BOCA-CONCRETO" (252.511 47.638) (470.011 -329.083) (448.361 -341.583) (230.861 35.138))
   ("P" "BOCA-SOLEIRA" (-223.002 -128.75) (218.671 126.25) (261.171 52.638) (470.011 -329.083) (475.011 -337.743) (-487.355 -893.366) (-492.355 -884.705) (-180.502 -202.362))
   ("L" "BOCA-OCULTO" (-125.141 -72.25) (-125.141 -170.4))
   ("L" "BOCA-OCULTO" (124.859 72.088) (124.859 -26.062))
   ("L" "BOCA-EIXO" (0 69.282) (0 -144.338))))
  (list "BSTC 3,00 - EXTRAPOLADO" "BEAA30_BSTC300_PL"
   '(("P" "BOCA-CONCRETO" (-257.21 -148.5) (252.013 145.5) (302.013 58.897) (-207.21 -235.103))
   ("P" "BOCA-CONCRETO" (-207.21 -235.103) (-590.352 -1056.754) (-545.056 -1030.603) (-161.913 -208.951))
   ("P" "BOCA-CONCRETO" (302.013 58.897) (562.013 -391.436) (536.033 -406.436) (276.033 43.897))
   ("P" "BOCA-SOLEIRA" (-265.87 -153.5) (260.674 150.5) (310.674 63.897) (562.013 -391.436) (567.013 -400.096) (-585.352 -1065.414) (-590.352 -1056.754) (-215.87 -240.103))
   ("L" "BOCA-OCULTO" (-149.822 -86.5) (-149.822 -201.97))
   ("L" "BOCA-OCULTO" (150.178 86.705) (150.178 -28.765))
   ("L" "BOCA-EIXO" (0 69.282) (0 -161.658))))
  (list "BDTC 1,00 - BEAA 17" "BEAA30_BDTC100_PL"
   '(("P" "BOCA-CONCRETO" (-166.277 -96) (167.143 96.5) (182.143 70.519) (-151.277 -121.981))
   ("P" "BOCA-CONCRETO" (-151.277 -121.981) (-272.851 -382.697) (-242.654 -365.263) (-121.079 -104.546))
   ("P" "BOCA-CONCRETO" (182.143 70.519) (264.643 -72.375) (247.322 -82.375) (164.822 60.519))
   ("P" "BOCA-SOLEIRA" (-174.937 -101) (175.803 101.5) (190.803 75.519) (264.643 -72.375) (269.643 -81.035) (-267.851 -391.357) (-272.851 -382.697) (-159.937 -126.981))
   ("L" "BOCA-OCULTO" (-126.44 -73) (-126.44 -107.641))
   ("L" "BOCA-OCULTO" (-26.44 -15.265) (-26.44 -49.906))
   ("L" "BOCA-OCULTO" (26.44 15.265) (26.44 -19.376))
   ("L" "BOCA-OCULTO" (126.44 73) (126.44 38.359))
   ("L" "BOCA-EIXO" (0 69.282) (0 -80.829))))
  (list "BDTC 1,20 - BEAA 18" "BEAA30_BDTC120_PL"
   '(("P" "BOCA-CONCRETO" (-195.722 -113) (193.99 112) (213.99 77.359) (-175.722 -147.641))
   ("P" "BOCA-CONCRETO" (-175.722 -147.641) (-308.348 -432.059) (-278.151 -414.624) (-145.524 -130.207))
   ("P" "BOCA-CONCRETO" (213.99 77.359) (303.99 -78.526) (286.669 -88.526) (196.669 67.359))
   ("P" "BOCA-SOLEIRA" (-204.382 -118) (202.65 117) (222.65 82.359) (303.99 -78.526) (308.99 -87.186) (-303.348 -440.719) (-308.348 -432.059) (-184.382 -152.641))
   ("L" "BOCA-OCULTO" (-148.956 -86) (-148.956 -132.188))
   ("L" "BOCA-OCULTO" (-28.956 -16.718) (-28.956 -62.906))
   ("L" "BOCA-OCULTO" (28.956 16.718) (28.956 -29.47))
   ("L" "BOCA-OCULTO" (148.956 86) (148.956 39.812))
   ("L" "BOCA-EIXO" (0 69.282) (0 -92.376))))
  (list "BDTC 1,50 - BEAA 19" "BEAA30_BDTC150_PL"
   '(("P" "BOCA-CONCRETO" (-234.693 -135.5) (228.631 132) (253.631 88.699) (-209.693 -178.801))
   ("P" "BOCA-CONCRETO" (-209.693 -178.801) (-401.264 -589.627) (-371.067 -572.193) (-179.496 -161.367))
   ("P" "BOCA-CONCRETO" (253.631 88.699) (383.631 -136.468) (366.31 -146.468) (236.31 78.699))
   ("P" "BOCA-SOLEIRA" (-243.353 -140.5) (237.291 137) (262.291 93.699) (383.631 -136.468) (388.631 -145.128) (-396.264 -598.287) (-401.264 -589.627) (-218.353 -183.801))
   ("L" "BOCA-OCULTO" (-180.999 -104.5) (-180.999 -162.235))
   ("L" "BOCA-OCULTO" (-30.999 -17.897) (-30.999 -75.632))
   ("L" "BOCA-OCULTO" (30.999 17.897) (30.999 -39.838))
   ("L" "BOCA-OCULTO" (180.999 104.5) (180.999 46.765))
   ("L" "BOCA-EIXO" (0 69.282) (0 -103.923))))
  (list "BDTC 2,00 - EXTRAPOLADO" "BEAA30_BDTC200_PL"
   '(("P" "BOCA-CONCRETO" (-308.305 -178) (299.645 173) (332.145 116.708) (-275.805 -234.292))
   ("P" "BOCA-CONCRETO" (-275.805 -234.292) (-530.005 -779.426) (-492.259 -757.633) (-238.058 -212.499))
   ("P" "BOCA-CONCRETO" (332.145 116.708) (504.645 -182.07) (482.994 -194.57) (310.494 104.208))
   ("P" "BOCA-SOLEIRA" (-316.965 -183) (308.305 178) (340.805 121.708) (504.645 -182.07) (509.645 -190.731) (-525.005 -788.086) (-530.005 -779.426) (-284.465 -239.292))
   ("L" "BOCA-OCULTO" (-236.425 -136.5) (-236.425 -211.556))
   ("L" "BOCA-OCULTO" (-36.425 -21.03) (-36.425 -96.085))
   ("L" "BOCA-OCULTO" (36.425 21.03) (36.425 -54.026))
   ("L" "BOCA-OCULTO" (236.425 136.5) (236.425 61.444))
   ("L" "BOCA-EIXO" (0 69.282) (0 -121.244))))
  (list "BDTC 2,50 - EXTRAPOLADO" "BEAA30_BDTC250_PL"
   '(("P" "BOCA-CONCRETO" (-380.618 -219.75) (371.092 214.25) (413.592 140.638) (-338.118 -293.362))
   ("P" "BOCA-CONCRETO" (-338.118 -293.362) (-658.632 -980.705) (-620.885 -958.912) (-300.371 -271.569))
   ("P" "BOCA-CONCRETO" (413.592 140.638) (631.092 -236.083) (609.441 -248.583) (391.941 128.138))
   ("P" "BOCA-SOLEIRA" (-389.278 -224.75) (379.752 219.25) (422.252 145.638) (631.092 -236.083) (636.092 -244.743) (-653.632 -989.366) (-658.632 -980.705) (-346.778 -298.362))
   ("L" "BOCA-OCULTO" (-291.418 -168.25) (-291.418 -266.4))
   ("L" "BOCA-OCULTO" (-41.418 -23.912) (-41.418 -122.062))
   ("L" "BOCA-OCULTO" (41.418 23.912) (41.418 -74.237))
   ("L" "BOCA-OCULTO" (291.418 168.25) (291.418 70.1))
   ("L" "BOCA-EIXO" (0 69.282) (0 -144.338))))
  (list "BDTC 3,00 - EXTRAPOLADO" "BEAA30_BDTC300_PL"
   '(("P" "BOCA-CONCRETO" (-453.797 -262) (441.673 255) (491.673 168.397) (-403.797 -348.603))
   ("P" "BOCA-CONCRETO" (-403.797 -348.603) (-786.94 -1170.254) (-741.644 -1144.103) (-358.501 -322.451))
   ("P" "BOCA-CONCRETO" (491.673 168.397) (751.673 -281.936) (725.692 -296.936) (465.692 153.397))
   ("P" "BOCA-SOLEIRA" (-462.458 -267) (450.333 260) (500.333 173.397) (751.673 -281.936) (756.673 -290.596) (-781.94 -1178.914) (-786.94 -1170.254) (-412.458 -353.603))
   ("L" "BOCA-OCULTO" (-346.41 -200) (-346.41 -315.47))
   ("L" "BOCA-OCULTO" (-46.41 -26.795) (-46.41 -142.265))
   ("L" "BOCA-OCULTO" (46.41 26.795) (46.41 -88.675))
   ("L" "BOCA-OCULTO" (346.41 200) (346.41 84.53))
   ("L" "BOCA-EIXO" (0 69.282) (0 -161.658))))
  (list "BTTC 1,00 - BEAA 20" "BEAA30_BTTC100_PL"
   '(("P" "BOCA-CONCRETO" (-242.487 -140) (246.817 142.5) (261.817 116.519) (-227.487 -165.981))
   ("P" "BOCA-CONCRETO" (-227.487 -165.981) (-349.061 -426.697) (-318.864 -409.263) (-197.29 -148.546))
   ("P" "BOCA-CONCRETO" (261.817 116.519) (344.317 -26.375) (326.997 -36.375) (244.497 106.519))
   ("P" "BOCA-SOLEIRA" (-251.147 -145) (255.477 147.5) (270.477 121.519) (344.317 -26.375) (349.317 -35.035) (-344.061 -435.357) (-349.061 -426.697) (-236.147 -170.981))
   ("L" "BOCA-OCULTO" (-202.65 -117) (-202.65 -151.641))
   ("L" "BOCA-OCULTO" (-102.65 -59.265) (-102.65 -93.906))
   ("L" "BOCA-OCULTO" (-50 -28.868) (-50 -63.509))
   ("L" "BOCA-OCULTO" (50 28.868) (50 -5.774))
   ("L" "BOCA-OCULTO" (102.65 59.265) (102.65 24.624))
   ("L" "BOCA-OCULTO" (202.65 117) (202.65 82.359))
   ("L" "BOCA-EIXO" (0 69.282) (0 -80.829))))
  (list "BTTC 1,20 - BEAA 21" "BEAA30_BTTC120_PL"
   '(("P" "BOCA-CONCRETO" (-284.922 -164.5) (282.324 163) (302.324 128.359) (-264.922 -199.141))
   ("P" "BOCA-CONCRETO" (-264.922 -199.141) (-397.549 -483.559) (-367.351 -466.124) (-234.725 -181.707))
   ("P" "BOCA-CONCRETO" (302.324 128.359) (392.324 -27.526) (375.004 -37.526) (285.004 118.359))
   ("P" "BOCA-SOLEIRA" (-293.583 -169.5) (290.985 168) (310.985 133.359) (392.324 -27.526) (397.324 -36.186) (-392.549 -492.219) (-397.549 -483.559) (-273.583 -204.141))
   ("L" "BOCA-OCULTO" (-238.157 -137.5) (-238.157 -183.688))
   ("L" "BOCA-OCULTO" (-118.157 -68.218) (-118.157 -114.406))
   ("L" "BOCA-OCULTO" (-60 -34.641) (-60 -80.829))
   ("L" "BOCA-OCULTO" (60 34.641) (60 -11.547))
   ("L" "BOCA-OCULTO" (118.157 68.218) (118.157 22.03))
   ("L" "BOCA-OCULTO" (238.157 137.5) (238.157 91.312))
   ("L" "BOCA-EIXO" (0 69.282) (0 -92.376))))
  (list "BTTC 1,50 - BEAA 22" "BEAA30_BTTC150_PL"
   '(("P" "BOCA-CONCRETO" (-340.781 -196.75) (334.719 193.25) (359.719 149.949) (-315.781 -240.051))
   ("P" "BOCA-CONCRETO" (-315.781 -240.051) (-507.352 -650.877) (-477.155 -633.443) (-285.584 -222.617))
   ("P" "BOCA-CONCRETO" (359.719 149.949) (489.719 -75.218) (472.398 -85.218) (342.398 139.949))
   ("P" "BOCA-SOLEIRA" (-349.441 -201.75) (343.379 198.25) (368.379 154.949) (489.719 -75.218) (494.719 -83.878) (-502.352 -659.537) (-507.352 -650.877) (-324.441 -245.051))
   ("L" "BOCA-OCULTO" (-287.087 -165.75) (-287.087 -223.485))
   ("L" "BOCA-OCULTO" (-137.087 -79.147) (-137.087 -136.882))
   ("L" "BOCA-OCULTO" (-75 -43.301) (-75 -101.036))
   ("L" "BOCA-OCULTO" (75 43.301) (75 -14.434))
   ("L" "BOCA-OCULTO" (137.087 79.147) (137.087 21.412))
   ("L" "BOCA-OCULTO" (287.087 165.75) (287.087 108.015))
   ("L" "BOCA-EIXO" (0 69.282) (0 -103.923))))
  (list "BTTC 2,00 - EXTRAPOLADO" "BEAA30_BTTC200_PL"
   '(("P" "BOCA-CONCRETO" (-444.704 -256.75) (436.044 251.75) (468.544 195.458) (-412.204 -313.042))
   ("P" "BOCA-CONCRETO" (-412.204 -313.042) (-666.404 -858.176) (-628.658 -836.383) (-374.457 -291.249))
   ("P" "BOCA-CONCRETO" (468.544 195.458) (641.044 -103.32) (619.393 -115.82) (446.893 182.958))
   ("P" "BOCA-SOLEIRA" (-453.364 -261.75) (444.704 256.75) (477.204 200.458) (641.044 -103.32) (646.044 -111.981) (-661.404 -866.836) (-666.404 -858.176) (-420.864 -318.042))
   ("L" "BOCA-OCULTO" (-372.824 -215.25) (-372.824 -290.306))
   ("L" "BOCA-OCULTO" (-172.824 -99.78) (-172.824 -174.835))
   ("L" "BOCA-OCULTO" (-100 -57.735) (-100 -132.791))
   ("L" "BOCA-OCULTO" (100 57.735) (100 -17.321))
   ("L" "BOCA-OCULTO" (172.824 99.78) (172.824 24.724))
   ("L" "BOCA-OCULTO" (372.824 215.25) (372.824 140.194))
   ("L" "BOCA-EIXO" (0 69.282) (0 -121.244))))
  (list "BTTC 2,50 - EXTRAPOLADO" "BEAA30_BTTC250_PL"
   '(("P" "BOCA-CONCRETO" (-547.328 -316) (537.802 310.5) (580.302 236.888) (-504.828 -389.612))
   ("P" "BOCA-CONCRETO" (-504.828 -389.612) (-825.341 -1076.955) (-787.595 -1055.162) (-467.081 -367.819))
   ("P" "BOCA-CONCRETO" (580.302 236.888) (797.802 -139.833) (776.151 -152.333) (558.651 224.388))
   ("P" "BOCA-SOLEIRA" (-555.988 -321) (546.462 315.5) (588.962 241.888) (797.802 -139.833) (802.802 -148.493) (-820.341 -1085.616) (-825.341 -1076.955) (-513.488 -394.612))
   ("L" "BOCA-OCULTO" (-458.127 -264.5) (-458.127 -362.65))
   ("L" "BOCA-OCULTO" (-208.127 -120.162) (-208.127 -218.312))
   ("L" "BOCA-OCULTO" (-125 -72.169) (-125 -170.318))
   ("L" "BOCA-OCULTO" (125 72.169) (125 -25.981))
   ("L" "BOCA-OCULTO" (208.127 120.162) (208.127 22.013))
   ("L" "BOCA-OCULTO" (458.127 264.5) (458.127 166.35))
   ("L" "BOCA-EIXO" (0 69.282) (0 -144.338))))
  (list "BTTC 3,00 - EXTRAPOLADO" "BEAA30_BTTC300_PL"
   '(("P" "BOCA-CONCRETO" (-650.385 -375.5) (638.261 368.5) (688.261 281.897) (-600.385 -462.103))
   ("P" "BOCA-CONCRETO" (-600.385 -462.103) (-983.528 -1283.754) (-938.231 -1257.603) (-555.089 -435.951))
   ("P" "BOCA-CONCRETO" (688.261 281.897) (948.261 -168.436) (922.28 -183.436) (662.28 266.897))
   ("P" "BOCA-SOLEIRA" (-659.045 -380.5) (646.921 373.5) (696.921 286.897) (948.261 -168.436) (953.261 -177.096) (-978.528 -1292.414) (-983.528 -1283.754) (-609.045 -467.103))
   ("L" "BOCA-OCULTO" (-542.998 -313.5) (-542.998 -428.97))
   ("L" "BOCA-OCULTO" (-242.998 -140.295) (-242.998 -255.765))
   ("L" "BOCA-OCULTO" (-150 -86.603) (-150 -202.073))
   ("L" "BOCA-OCULTO" (150 86.603) (150 -28.868))
   ("L" "BOCA-OCULTO" (242.998 140.295) (242.998 24.825))
   ("L" "BOCA-OCULTO" (542.998 313.5) (542.998 198.03))
   ("L" "BOCA-EIXO" (0 69.282) (0 -161.658))))
 ))
 (list "BOCA_BEAA30_FRONTAL" (list
  (list "BSTC 1,00 - BEAA 14" "BEAA30_BSTC100_FR"
   '(("P" "BOCA-CONCRETO" (-86.179 0) (123.821 0) (123.821 142) (-86.179 142))
   ("E" "BOCA-CONCRETO" (0.235 50) 57.735 50)
   ("P" "BOCA-CONCRETO" (-86.179 0) (-86.179 142) (-321.824 25) (-321.824 0))
   ("L" "BOCA-CONCRETO" (-286.955 0) (-286.955 25))
   ("P" "BOCA-CONCRETO" (123.821 0) (123.821 142) (123.821 25) (123.821 0))
   ("L" "BOCA-CONCRETO" (103.821 0) (103.821 25))
   ("P" "BOCA-SOLEIRA" (-321.824 0) (133.821 0) (133.821 -65) (-321.824 -65))
   ("L" "BOCA-OCULTO" (-321.824 -25) (133.821 -25))
   ("P" "BOCA-SOLEIRA" (-321.824 -65) (133.821 -65) (133.821 -70) (-321.824 -70))))
  (list "BSTC 1,20 - BEAA 15" "BEAA30_BSTC120_FR"
   '(("P" "BOCA-CONCRETO" (-100.406 0) (144.594 0) (144.594 163) (-100.406 163))
   ("E" "BOCA-CONCRETO" (-0.218 60) 69.282 60)
   ("P" "BOCA-CONCRETO" (-100.406 0) (-100.406 163) (-357.473 30) (-357.473 0))
   ("L" "BOCA-CONCRETO" (-322.604 0) (-322.604 30))
   ("P" "BOCA-CONCRETO" (144.594 0) (144.594 163) (144.594 30) (144.594 0))
   ("L" "BOCA-CONCRETO" (124.594 0) (124.594 30))
   ("P" "BOCA-SOLEIRA" (-357.473 0) (154.594 0) (154.594 -65) (-357.473 -65))
   ("L" "BOCA-OCULTO" (-357.473 -25) (154.594 -25))
   ("P" "BOCA-SOLEIRA" (-357.473 -65) (154.594 -65) (154.594 -70) (-357.473 -70))))
  (list "BSTC 1,50 - BEAA 16" "BEAA30_BSTC150_FR"
   '(("P" "BOCA-CONCRETO" (-120.132 0) (174.868 0) (174.868 194) (-120.132 194))
   ("E" "BOCA-CONCRETO" (-0.397 75) 86.603 75)
   ("P" "BOCA-CONCRETO" (-120.132 0) (-120.132 194) (-491.451 35) (-491.451 0))
   ("L" "BOCA-CONCRETO" (-456.582 0) (-456.582 35))
   ("P" "BOCA-CONCRETO" (174.868 0) (174.868 194) (174.868 35) (174.868 0))
   ("L" "BOCA-CONCRETO" (154.868 0) (154.868 35))
   ("P" "BOCA-SOLEIRA" (-491.451 0) (184.868 0) (184.868 -70) (-491.451 -70))
   ("L" "BOCA-OCULTO" (-491.451 -30) (184.868 -30))
   ("P" "BOCA-SOLEIRA" (-491.451 -70) (184.868 -70) (184.868 -75) (-491.451 -75))))
  (list "BSTC 2,00 - EXTRAPOLADO" "BEAA30_BSTC200_FR"
   '(("P" "BOCA-CONCRETO" (-160.972 0) (232.028 0) (232.028 244) (-160.972 244))
   ("E" "BOCA-CONCRETO" (-0.03 100) 115.47 100)
   ("P" "BOCA-CONCRETO" (-160.972 0) (-160.972 244) (-653.683 45) (-653.683 0))
   ("L" "BOCA-CONCRETO" (-610.097 0) (-610.097 45))
   ("P" "BOCA-CONCRETO" (232.028 0) (232.028 244) (232.028 45) (232.028 0))
   ("L" "BOCA-CONCRETO" (207.028 0) (207.028 45))
   ("P" "BOCA-SOLEIRA" (-653.683 0) (242.028 0) (242.028 -80) (-653.683 -80))
   ("L" "BOCA-OCULTO" (-653.683 -35) (242.028 -35))
   ("P" "BOCA-SOLEIRA" (-653.683 -80) (242.028 -80) (242.028 -85) (-653.683 -85))))
  (list "BSTC 2,50 - EXTRAPOLADO" "BEAA30_BSTC250_FR"
   '(("P" "BOCA-CONCRETO" (-198.425 0) (291.575 0) (291.575 294) (-198.425 294))
   ("E" "BOCA-CONCRETO" (-0.162 125) 144.338 125)
   ("P" "BOCA-CONCRETO" (-198.425 0) (-198.425 294) (-819.67 60) (-819.67 0))
   ("L" "BOCA-CONCRETO" (-776.083 0) (-776.083 60))
   ("P" "BOCA-CONCRETO" (291.575 0) (291.575 294) (291.575 60) (291.575 0))
   ("L" "BOCA-CONCRETO" (266.575 0) (266.575 60))
   ("P" "BOCA-SOLEIRA" (-819.67 0) (301.575 0) (301.575 -90) (-819.67 -90))
   ("L" "BOCA-OCULTO" (-819.67 -40) (301.575 -40))
   ("P" "BOCA-SOLEIRA" (-819.67 -90) (301.575 -90) (301.575 -95) (-819.67 -95))))
  (list "BSTC 3,00 - EXTRAPOLADO" "BEAA30_BSTC300_FR"
   '(("P" "BOCA-CONCRETO" (-239.265 0) (348.735 0) (348.735 344) (-239.265 344))
   ("E" "BOCA-CONCRETO" (0.205 150) 173.205 150)
   ("P" "BOCA-CONCRETO" (-239.265 0) (-239.265 344) (-981.902 70) (-981.902 0))
   ("L" "BOCA-CONCRETO" (-929.599 0) (-929.599 70))
   ("P" "BOCA-CONCRETO" (348.735 0) (348.735 344) (348.735 70) (348.735 0))
   ("L" "BOCA-CONCRETO" (318.735 0) (318.735 70))
   ("P" "BOCA-SOLEIRA" (-981.902 0) (358.735 0) (358.735 -95) (-981.902 -95))
   ("L" "BOCA-OCULTO" (-981.902 -40) (358.735 -40))
   ("P" "BOCA-SOLEIRA" (-981.902 -95) (358.735 -95) (358.735 -100) (-981.902 -100))))
  (list "BDTC 1,00 - BEAA 17" "BEAA30_BDTC100_FR"
   '(("P" "BOCA-CONCRETO" (-174.679 0) (210.321 0) (210.321 142) (-174.679 142))
   ("E" "BOCA-CONCRETO" (-88.265 50) 57.735 50)
   ("E" "BOCA-CONCRETO" (88.265 50) 57.735 50)
   ("P" "BOCA-CONCRETO" (-174.679 0) (-174.679 142) (-410.324 30) (-410.324 0))
   ("L" "BOCA-CONCRETO" (-375.455 0) (-375.455 30))
   ("P" "BOCA-CONCRETO" (210.321 0) (210.321 142) (210.321 30) (210.321 0))
   ("L" "BOCA-CONCRETO" (190.321 0) (190.321 30))
   ("P" "BOCA-SOLEIRA" (-410.324 0) (220.321 0) (220.321 -65) (-410.324 -65))
   ("L" "BOCA-OCULTO" (-410.324 -25) (220.321 -25))
   ("P" "BOCA-SOLEIRA" (-410.324 -65) (220.321 -65) (220.321 -70) (-410.324 -70))))
  (list "BDTC 1,20 - BEAA 18" "BEAA30_BDTC120_FR"
   '(("P" "BOCA-CONCRETO" (-202.906 0) (247.094 0) (247.094 163) (-202.906 163))
   ("E" "BOCA-CONCRETO" (-102.718 60) 69.282 60)
   ("E" "BOCA-CONCRETO" (102.718 60) 69.282 60)
   ("P" "BOCA-CONCRETO" (-202.906 0) (-202.906 163) (-459.973 35) (-459.973 0))
   ("L" "BOCA-CONCRETO" (-425.104 0) (-425.104 35))
   ("P" "BOCA-CONCRETO" (247.094 0) (247.094 163) (247.094 35) (247.094 0))
   ("L" "BOCA-CONCRETO" (227.094 0) (227.094 35))
   ("P" "BOCA-SOLEIRA" (-459.973 0) (257.094 0) (257.094 -65) (-459.973 -65))
   ("L" "BOCA-OCULTO" (-459.973 -25) (257.094 -25))
   ("P" "BOCA-SOLEIRA" (-459.973 -65) (257.094 -65) (257.094 -70) (-459.973 -70))))
  (list "BDTC 1,50 - BEAA 19" "BEAA30_BDTC150_FR"
   '(("P" "BOCA-CONCRETO" (-242.132 0) (292.868 0) (292.868 194) (-242.132 194))
   ("E" "BOCA-CONCRETO" (-122.397 75) 86.603 75)
   ("E" "BOCA-CONCRETO" (122.397 75) 86.603 75)
   ("P" "BOCA-CONCRETO" (-242.132 0) (-242.132 194) (-613.451 35) (-613.451 0))
   ("L" "BOCA-CONCRETO" (-578.582 0) (-578.582 35))
   ("P" "BOCA-CONCRETO" (292.868 0) (292.868 194) (292.868 35) (292.868 0))
   ("L" "BOCA-CONCRETO" (272.868 0) (272.868 35))
   ("P" "BOCA-SOLEIRA" (-613.451 0) (302.868 0) (302.868 -70) (-613.451 -70))
   ("L" "BOCA-OCULTO" (-613.451 -30) (302.868 -30))
   ("P" "BOCA-SOLEIRA" (-613.451 -70) (302.868 -70) (302.868 -75) (-613.451 -75))))
  (list "BDTC 2,00 - EXTRAPOLADO" "BEAA30_BDTC200_FR"
   '(("P" "BOCA-CONCRETO" (-318.472 0) (383.528 0) (383.528 244) (-318.472 244))
   ("E" "BOCA-CONCRETO" (-157.53 100) 115.47 100)
   ("E" "BOCA-CONCRETO" (157.53 100) 115.47 100)
   ("P" "BOCA-CONCRETO" (-318.472 0) (-318.472 244) (-811.183 45) (-811.183 0))
   ("L" "BOCA-CONCRETO" (-767.597 0) (-767.597 45))
   ("P" "BOCA-CONCRETO" (383.528 0) (383.528 244) (383.528 45) (383.528 0))
   ("L" "BOCA-CONCRETO" (358.528 0) (358.528 45))
   ("P" "BOCA-SOLEIRA" (-811.183 0) (393.528 0) (393.528 -80) (-811.183 -80))
   ("L" "BOCA-OCULTO" (-811.183 -35) (393.528 -35))
   ("P" "BOCA-SOLEIRA" (-811.183 -80) (393.528 -80) (393.528 -85) (-811.183 -85))))
  (list "BDTC 2,50 - EXTRAPOLADO" "BEAA30_BDTC250_FR"
   '(("P" "BOCA-CONCRETO" (-390.425 0) (477.575 0) (477.575 294) (-390.425 294))
   ("E" "BOCA-CONCRETO" (-192.162 125) 144.338 125)
   ("E" "BOCA-CONCRETO" (192.162 125) 144.338 125)
   ("P" "BOCA-CONCRETO" (-390.425 0) (-390.425 294) (-1011.67 60) (-1011.67 0))
   ("L" "BOCA-CONCRETO" (-968.083 0) (-968.083 60))
   ("P" "BOCA-CONCRETO" (477.575 0) (477.575 294) (477.575 60) (477.575 0))
   ("L" "BOCA-CONCRETO" (452.575 0) (452.575 60))
   ("P" "BOCA-SOLEIRA" (-1011.67 0) (487.575 0) (487.575 -90) (-1011.67 -90))
   ("L" "BOCA-OCULTO" (-1011.67 -40) (487.575 -40))
   ("P" "BOCA-SOLEIRA" (-1011.67 -90) (487.575 -90) (487.575 -95) (-1011.67 -95))))
  (list "BDTC 3,00 - EXTRAPOLADO" "BEAA30_BDTC300_FR"
   '(("P" "BOCA-CONCRETO" (-466.265 0) (567.735 0) (567.735 344) (-466.265 344))
   ("E" "BOCA-CONCRETO" (-226.795 150) 173.205 150)
   ("E" "BOCA-CONCRETO" (226.795 150) 173.205 150)
   ("P" "BOCA-CONCRETO" (-466.265 0) (-466.265 344) (-1208.902 70) (-1208.902 0))
   ("L" "BOCA-CONCRETO" (-1156.599 0) (-1156.599 70))
   ("P" "BOCA-CONCRETO" (567.735 0) (567.735 344) (567.735 70) (567.735 0))
   ("L" "BOCA-CONCRETO" (537.735 0) (537.735 70))
   ("P" "BOCA-SOLEIRA" (-1208.902 0) (577.735 0) (577.735 -95) (-1208.902 -95))
   ("L" "BOCA-OCULTO" (-1208.902 -40) (577.735 -40))
   ("P" "BOCA-SOLEIRA" (-1208.902 -95) (577.735 -95) (577.735 -100) (-1208.902 -100))))
  (list "BTTC 1,00 - BEAA 20" "BEAA30_BTTC100_FR"
   '(("P" "BOCA-CONCRETO" (-262.679 0) (302.321 0) (302.321 142) (-262.679 142))
   ("E" "BOCA-CONCRETO" (-176.265 50) 57.735 50)
   ("E" "BOCA-CONCRETO" (0 50) 57.735 50)
   ("E" "BOCA-CONCRETO" (176.265 50) 57.735 50)
   ("P" "BOCA-CONCRETO" (-262.679 0) (-262.679 142) (-498.324 35) (-498.324 0))
   ("L" "BOCA-CONCRETO" (-463.455 0) (-463.455 35))
   ("P" "BOCA-CONCRETO" (302.321 0) (302.321 142) (302.321 35) (302.321 0))
   ("L" "BOCA-CONCRETO" (282.321 0) (282.321 35))
   ("P" "BOCA-SOLEIRA" (-498.324 0) (312.321 0) (312.321 -65) (-498.324 -65))
   ("L" "BOCA-OCULTO" (-498.324 -25) (312.321 -25))
   ("P" "BOCA-SOLEIRA" (-498.324 -65) (312.321 -65) (312.321 -70) (-498.324 -70))))
  (list "BTTC 1,20 - BEAA 21" "BEAA30_BTTC120_FR"
   '(("P" "BOCA-CONCRETO" (-305.906 0) (349.094 0) (349.094 163) (-305.906 163))
   ("E" "BOCA-CONCRETO" (-205.718 60) 69.282 60)
   ("E" "BOCA-CONCRETO" (0 60) 69.282 60)
   ("E" "BOCA-CONCRETO" (205.718 60) 69.282 60)
   ("P" "BOCA-CONCRETO" (-305.906 0) (-305.906 163) (-562.973 40) (-562.973 0))
   ("L" "BOCA-CONCRETO" (-528.104 0) (-528.104 40))
   ("P" "BOCA-CONCRETO" (349.094 0) (349.094 163) (349.094 40) (349.094 0))
   ("L" "BOCA-CONCRETO" (329.094 0) (329.094 40))
   ("P" "BOCA-SOLEIRA" (-562.973 0) (359.094 0) (359.094 -65) (-562.973 -65))
   ("L" "BOCA-OCULTO" (-562.973 -25) (359.094 -25))
   ("P" "BOCA-SOLEIRA" (-562.973 -65) (359.094 -65) (359.094 -70) (-562.973 -70))))
  (list "BTTC 1,50 - BEAA 22" "BEAA30_BTTC150_FR"
   '(("P" "BOCA-CONCRETO" (-364.632 0) (415.368 0) (415.368 194) (-364.632 194))
   ("E" "BOCA-CONCRETO" (-244.897 75) 86.603 75)
   ("E" "BOCA-CONCRETO" (0 75) 86.603 75)
   ("E" "BOCA-CONCRETO" (244.897 75) 86.603 75)
   ("P" "BOCA-CONCRETO" (-364.632 0) (-364.632 194) (-735.951 40) (-735.951 0))
   ("L" "BOCA-CONCRETO" (-701.082 0) (-701.082 40))
   ("P" "BOCA-CONCRETO" (415.368 0) (415.368 194) (415.368 40) (415.368 0))
   ("L" "BOCA-CONCRETO" (395.368 0) (395.368 40))
   ("P" "BOCA-SOLEIRA" (-735.951 0) (425.368 0) (425.368 -70) (-735.951 -70))
   ("L" "BOCA-OCULTO" (-735.951 -30) (425.368 -30))
   ("P" "BOCA-SOLEIRA" (-735.951 -70) (425.368 -70) (425.368 -75) (-735.951 -75))))
  (list "BTTC 2,00 - EXTRAPOLADO" "BEAA30_BTTC200_FR"
   '(("P" "BOCA-CONCRETO" (-475.972 0) (541.028 0) (541.028 244) (-475.972 244))
   ("E" "BOCA-CONCRETO" (-315.03 100) 115.47 100)
   ("E" "BOCA-CONCRETO" (0 100) 115.47 100)
   ("E" "BOCA-CONCRETO" (315.03 100) 115.47 100)
   ("P" "BOCA-CONCRETO" (-475.972 0) (-475.972 244) (-968.683 55) (-968.683 0))
   ("L" "BOCA-CONCRETO" (-925.097 0) (-925.097 55))
   ("P" "BOCA-CONCRETO" (541.028 0) (541.028 244) (541.028 55) (541.028 0))
   ("L" "BOCA-CONCRETO" (516.028 0) (516.028 55))
   ("P" "BOCA-SOLEIRA" (-968.683 0) (551.028 0) (551.028 -80) (-968.683 -80))
   ("L" "BOCA-OCULTO" (-968.683 -35) (551.028 -35))
   ("P" "BOCA-SOLEIRA" (-968.683 -80) (551.028 -80) (551.028 -85) (-968.683 -85))))
  (list "BTTC 2,50 - EXTRAPOLADO" "BEAA30_BTTC250_FR"
   '(("P" "BOCA-CONCRETO" (-582.925 0) (670.075 0) (670.075 294) (-582.925 294))
   ("E" "BOCA-CONCRETO" (-384.662 125) 144.338 125)
   ("E" "BOCA-CONCRETO" (0 125) 144.338 125)
   ("E" "BOCA-CONCRETO" (384.662 125) 144.338 125)
   ("P" "BOCA-CONCRETO" (-582.925 0) (-582.925 294) (-1204.17 65) (-1204.17 0))
   ("L" "BOCA-CONCRETO" (-1160.583 0) (-1160.583 65))
   ("P" "BOCA-CONCRETO" (670.075 0) (670.075 294) (670.075 65) (670.075 0))
   ("L" "BOCA-CONCRETO" (645.075 0) (645.075 65))
   ("P" "BOCA-SOLEIRA" (-1204.17 0) (680.075 0) (680.075 -90) (-1204.17 -90))
   ("L" "BOCA-OCULTO" (-1204.17 -40) (680.075 -40))
   ("P" "BOCA-SOLEIRA" (-1204.17 -90) (680.075 -90) (680.075 -95) (-1204.17 -95))))
  (list "BTTC 3,00 - EXTRAPOLADO" "BEAA30_BTTC300_FR"
   '(("P" "BOCA-CONCRETO" (-693.265 0) (794.735 0) (794.735 344) (-693.265 344))
   ("E" "BOCA-CONCRETO" (-453.795 150) 173.205 150)
   ("E" "BOCA-CONCRETO" (0 150) 173.205 150)
   ("E" "BOCA-CONCRETO" (453.795 150) 173.205 150)
   ("P" "BOCA-CONCRETO" (-693.265 0) (-693.265 344) (-1435.902 80) (-1435.902 0))
   ("L" "BOCA-CONCRETO" (-1383.599 0) (-1383.599 80))
   ("P" "BOCA-CONCRETO" (794.735 0) (794.735 344) (794.735 80) (794.735 0))
   ("L" "BOCA-CONCRETO" (764.735 0) (764.735 80))
   ("P" "BOCA-SOLEIRA" (-1435.902 0) (804.735 0) (804.735 -95) (-1435.902 -95))
   ("L" "BOCA-OCULTO" (-1435.902 -40) (804.735 -40))
   ("P" "BOCA-SOLEIRA" (-1435.902 -95) (804.735 -95) (804.735 -100) (-1435.902 -100))))
 ))
 (list "BOCA_BEAA45_PLANTA" (list
  (list "BSTC 1,00 - BEAA 25" "BEAA45_BSTC100_PL"
   '(("P" "BOCA-CONCRETO" (-93.338 -93.338) (94.045 94.045) (115.258 72.832) (-72.125 -114.551))
   ("P" "BOCA-CONCRETO" (-72.125 -114.551) (-205.658 -481.429) (-172.194 -447.966) (-38.662 -81.088))
   ("P" "BOCA-CONCRETO" (115.258 72.832) (200.669 -75.103) (186.028 -89.744) (100.617 58.191))
   ("P" "BOCA-SOLEIRA" (-100.409 -100.409) (101.116 101.116) (122.329 79.903) (200.669 -75.103) (207.74 -82.174) (-198.586 -488.5) (-205.658 -481.429) (-79.196 -121.622))
   ("L" "BOCA-OCULTO" (-50.205 -50.205) (-50.205 -92.631))
   ("L" "BOCA-OCULTO" (49.795 49.795) (49.795 7.369))
   ("L" "BOCA-EIXO" (0 84.853) (0 -98.995))))
  (list "BSTC 1,20 - BEAA 26" "BEAA45_BSTC120_PL"
   '(("P" "BOCA-CONCRETO" (-112.784 -112.784) (109.955 109.955) (138.239 81.671) (-84.499 -141.068))
   ("P" "BOCA-CONCRETO" (-84.499 -141.068) (-230.171 -541.298) (-196.708 -507.835) (-51.036 -107.605))
   ("P" "BOCA-CONCRETO" (138.239 81.671) (231.414 -79.713) (216.773 -94.354) (123.598 67.03))
   ("P" "BOCA-SOLEIRA" (-119.855 -119.855) (117.026 117.026) (145.31 88.742) (231.414 -79.713) (238.485 -86.784) (-223.1 -548.369) (-230.171 -541.298) (-91.57 -148.139))
   ("L" "BOCA-OCULTO" (-59.751 -59.751) (-59.751 -116.319))
   ("L" "BOCA-OCULTO" (60.249 60.249) (60.249 3.681))
   ("L" "BOCA-EIXO" (0 84.853) (0 -113.137))))
  (list "BSTC 1,50 - BEAA 27" "BEAA45_BSTC150_PL"
   '(("P" "BOCA-CONCRETO" (-140.714 -140.714) (127.986 127.986) (163.342 92.631) (-105.359 -176.07))
   ("P" "BOCA-CONCRETO" (-105.359 -176.07) (-315.774 -754.18) (-282.311 -720.717) (-71.896 -142.606))
   ("P" "BOCA-CONCRETO" (163.342 92.631) (297.928 -140.479) (283.287 -155.12) (148.701 77.99))
   ("P" "BOCA-SOLEIRA" (-147.785 -147.785) (135.057 135.057) (170.413 99.702) (297.928 -140.479) (304.999 -147.55) (-308.703 -761.251) (-315.774 -754.18) (-112.43 -183.141))
   ("L" "BOCA-OCULTO" (-74.953 -74.953) (-74.953 -145.664))
   ("L" "BOCA-OCULTO" (75.047 75.047) (75.047 4.336))
   ("L" "BOCA-EIXO" (0 84.853) (0 -127.279))))
  (list "BSTC 2,00 - EXTRAPOLADO" "BEAA45_BSTC200_PL"
   '(("P" "BOCA-CONCRETO" (-187.737 -187.737) (170.766 170.766) (216.728 124.804) (-141.775 -233.699))
   ("P" "BOCA-CONCRETO" (-141.775 -233.699) (-420.979 -1000.807) (-379.151 -958.978) (-99.946 -191.87))
   ("P" "BOCA-CONCRETO" (216.728 124.804) (395.313 -184.514) (377.012 -202.815) (198.427 106.503))
   ("P" "BOCA-SOLEIRA" (-194.808 -194.808) (177.837 177.837) (223.799 131.875) (395.313 -184.514) (402.384 -191.585) (-413.908 -1007.878) (-420.979 -1000.807) (-148.846 -240.77))
   ("L" "BOCA-OCULTO" (-100.056 -100.056) (-100.056 -191.979))
   ("L" "BOCA-OCULTO" (99.944 99.944) (99.944 8.021))
   ("L" "BOCA-EIXO" (0 84.853) (0 -148.492))))
  (list "BSTC 2,50 - EXTRAPOLADO" "BEAA45_BSTC250_PL"
   '(("P" "BOCA-CONCRETO" (-234.759 -234.759) (213.546 213.546) (273.65 153.442) (-174.655 -294.864))
   ("P" "BOCA-CONCRETO" (-174.655 -294.864) (-526.696 -1262.087) (-484.867 -1220.258) (-132.826 -253.035))
   ("P" "BOCA-CONCRETO" (273.65 153.442) (498.823 -236.568) (480.522 -254.869) (255.349 135.141))
   ("P" "BOCA-SOLEIRA" (-241.831 -241.831) (220.617 220.617) (280.721 160.513) (498.823 -236.568) (505.894 -243.639) (-519.625 -1269.158) (-526.696 -1262.087) (-181.726 -301.935))
   ("L" "BOCA-OCULTO" (-125.158 -125.158) (-125.158 -245.366))
   ("L" "BOCA-OCULTO" (124.842 124.842) (124.842 4.634))
   ("L" "BOCA-EIXO" (0 84.853) (0 -176.777))))
  (list "BSTC 3,00 - EXTRAPOLADO" "BEAA45_BSTC300_PL"
   '(("P" "BOCA-CONCRETO" (-281.428 -281.428) (255.973 255.973) (326.683 185.262) (-210.718 -352.139))
   ("P" "BOCA-CONCRETO" (-210.718 -352.139) (-631.548 -1508.36) (-581.353 -1458.166) (-160.523 -301.944))
   ("P" "BOCA-CONCRETO" (326.683 185.262) (595.855 -280.957) (573.894 -302.919) (304.722 163.3))
   ("P" "BOCA-SOLEIRA" (-288.5 -288.5) (263.044 263.044) (333.754 192.333) (595.855 -280.957) (602.926 -288.028) (-624.477 -1515.431) (-631.548 -1508.36) (-217.789 -359.21))
   ("L" "BOCA-OCULTO" (-149.907 -149.907) (-149.907 -291.328))
   ("L" "BOCA-OCULTO" (150.093 150.093) (150.093 8.672))
   ("L" "BOCA-EIXO" (0 84.853) (0 -197.99))))
  (list "BDTC 1,00 - BEAA 28" "BEAA45_BDTC100_PL"
   '(("P" "BOCA-CONCRETO" (-169.706 -169.706) (173.241 173.241) (194.454 152.028) (-148.492 -190.919))
   ("P" "BOCA-CONCRETO" (-148.492 -190.919) (-282.025 -557.797) (-248.562 -524.334) (-115.029 -157.456))
   ("P" "BOCA-CONCRETO" (194.454 152.028) (279.865 4.093) (265.224 -10.548) (179.813 137.387))
   ("P" "BOCA-SOLEIRA" (-176.777 -176.777) (180.312 180.312) (201.525 159.099) (279.865 4.093) (286.936 -2.978) (-274.954 -564.868) (-282.025 -557.797) (-155.563 -197.99))
   ("L" "BOCA-OCULTO" (-126.572 -126.572) (-126.572 -168.999))
   ("L" "BOCA-OCULTO" (-26.572 -26.572) (-26.572 -68.999))
   ("L" "BOCA-OCULTO" (26.572 26.572) (26.572 -15.854))
   ("L" "BOCA-OCULTO" (126.572 126.572) (126.572 84.146))
   ("L" "BOCA-EIXO" (0 84.853) (0 -98.995))))
  (list "BDTC 1,20 - BEAA 29" "BEAA45_BDTC120_PL"
   '(("P" "BOCA-CONCRETO" (-201.879 -201.879) (197.636 197.636) (225.921 169.352) (-173.595 -230.163))
   ("P" "BOCA-CONCRETO" (-173.595 -230.163) (-319.267 -630.394) (-285.804 -596.931) (-140.132 -196.7))
   ("P" "BOCA-CONCRETO" (225.921 169.352) (319.095 7.968) (304.454 -6.673) (211.28 154.711))
   ("P" "BOCA-SOLEIRA" (-208.95 -208.95) (204.707 204.707) (232.992 176.423) (319.095 7.968) (326.167 0.897) (-312.196 -637.465) (-319.267 -630.394) (-180.666 -237.234))
   ("L" "BOCA-OCULTO" (-148.846 -148.846) (-148.846 -205.415))
   ("L" "BOCA-OCULTO" (-28.846 -28.846) (-28.846 -85.415))
   ("L" "BOCA-OCULTO" (28.846 28.846) (28.846 -27.723))
   ("L" "BOCA-OCULTO" (148.846 148.846) (148.846 92.277))
   ("L" "BOCA-EIXO" (0 84.853) (0 -113.137))))
  (list "BDTC 1,50 - BEAA 30" "BEAA45_BDTC150_PL"
   '(("P" "BOCA-CONCRETO" (-243.245 -243.245) (230.517 230.517) (265.872 195.161) (-207.889 -278.6))
   ("P" "BOCA-CONCRETO" (-207.889 -278.6) (-418.304 -856.711) (-384.841 -823.247) (-174.426 -245.137))
   ("P" "BOCA-CONCRETO" (265.872 195.161) (400.458 -37.948) (385.817 -52.589) (251.231 180.52))
   ("P" "BOCA-SOLEIRA" (-250.316 -250.316) (237.588 237.588) (272.943 202.233) (400.458 -37.948) (407.529 -45.019) (-411.233 -863.782) (-418.304 -856.711) (-214.96 -285.671))
   ("L" "BOCA-OCULTO" (-181.019 -181.019) (-181.019 -251.73))
   ("L" "BOCA-OCULTO" (-31.019 -31.019) (-31.019 -101.73))
   ("L" "BOCA-OCULTO" (31.019 31.019) (31.019 -39.691))
   ("L" "BOCA-OCULTO" (181.019 181.019) (181.019 110.309))
   ("L" "BOCA-EIXO" (0 84.853) (0 -127.279))))
  (list "BDTC 2,00 - EXTRAPOLADO" "BEAA45_BDTC200_PL"
   '(("P" "BOCA-CONCRETO" (-319.259 -319.259) (302.288 302.288) (348.25 256.326) (-273.297 -365.221))
   ("P" "BOCA-CONCRETO" (-273.297 -365.221) (-552.501 -1132.329) (-510.672 -1090.5) (-231.468 -323.392))
   ("P" "BOCA-CONCRETO" (348.25 256.326) (526.835 -52.992) (508.534 -71.294) (329.949 238.025))
   ("P" "BOCA-SOLEIRA" (-326.33 -326.33) (309.359 309.359) (355.321 263.397) (526.835 -52.992) (533.906 -60.063) (-545.43 -1139.4) (-552.501 -1132.329) (-280.368 -372.292))
   ("L" "BOCA-OCULTO" (-236.527 -236.527) (-236.527 -328.451))
   ("L" "BOCA-OCULTO" (-36.527 -36.527) (-36.527 -128.451))
   ("L" "BOCA-OCULTO" (36.527 36.527) (36.527 -55.397))
   ("L" "BOCA-OCULTO" (236.527 236.527) (236.527 144.603))
   ("L" "BOCA-EIXO" (0 84.853) (0 -148.492))))
  (list "BDTC 2,50 - EXTRAPOLADO" "BEAA45_BDTC250_PL"
   '(("P" "BOCA-CONCRETO" (-395.273 -395.273) (374.059 374.059) (434.164 313.955) (-335.169 -455.377))
   ("P" "BOCA-CONCRETO" (-335.169 -455.377) (-687.209 -1422.6) (-645.38 -1380.771) (-293.34 -413.548))
   ("P" "BOCA-CONCRETO" (434.164 313.955) (659.336 -76.055) (641.035 -94.356) (415.862 295.654))
   ("P" "BOCA-SOLEIRA" (-402.344 -402.344) (381.131 381.131) (441.235 321.026) (659.336 -76.055) (666.407 -83.126) (-680.138 -1429.671) (-687.209 -1422.6) (-342.24 -462.448))
   ("L" "BOCA-OCULTO" (-291.328 -291.328) (-291.328 -411.536))
   ("L" "BOCA-OCULTO" (-41.328 -41.328) (-41.328 -161.536))
   ("L" "BOCA-OCULTO" (41.328 41.328) (41.328 -78.88))
   ("L" "BOCA-OCULTO" (291.328 291.328) (291.328 171.12))
   ("L" "BOCA-EIXO" (0 84.853) (0 -176.777))))
  (list "BDTC 3,00 - EXTRAPOLADO" "BEAA45_BDTC300_PL"
   '(("P" "BOCA-CONCRETO" (-470.933 -470.933) (445.477 445.477) (516.188 374.767) (-400.222 -541.644))
   ("P" "BOCA-CONCRETO" (-400.222 -541.644) (-821.053 -1697.865) (-770.858 -1647.67) (-350.028 -491.449))
   ("P" "BOCA-CONCRETO" (516.188 374.767) (785.36 -91.453) (763.398 -113.414) (494.226 352.805))
   ("P" "BOCA-SOLEIRA" (-478.004 -478.004) (452.548 452.548) (523.259 381.838) (785.36 -91.453) (792.431 -98.524) (-813.981 -1704.936) (-821.053 -1697.865) (-407.294 -548.715))
   ("L" "BOCA-OCULTO" (-346.482 -346.482) (-346.482 -487.904))
   ("L" "BOCA-OCULTO" (-46.482 -46.482) (-46.482 -187.904))
   ("L" "BOCA-OCULTO" (46.482 46.482) (46.482 -94.939))
   ("L" "BOCA-OCULTO" (346.482 346.482) (346.482 205.061))
   ("L" "BOCA-EIXO" (0 84.853) (0 -197.99))))
  (list "BTTC 1,00 - BEAA 31" "BEAA45_BTTC100_PL"
   '(("P" "BOCA-CONCRETO" (-246.073 -246.073) (248.902 248.902) (270.115 227.688) (-224.86 -267.286))
   ("P" "BOCA-CONCRETO" (-224.86 -267.286) (-358.393 -634.164) (-324.929 -600.701) (-191.397 -233.823))
   ("P" "BOCA-CONCRETO" (270.115 227.688) (355.525 79.753) (340.884 65.112) (255.474 213.047))
   ("P" "BOCA-SOLEIRA" (-253.144 -253.144) (255.973 255.973) (277.186 234.759) (355.525 79.753) (362.596 72.682) (-351.322 -641.235) (-358.393 -634.164) (-231.931 -274.357))
   ("L" "BOCA-OCULTO" (-202.94 -202.94) (-202.94 -245.366))
   ("L" "BOCA-OCULTO" (-102.94 -102.94) (-102.94 -145.366))
   ("L" "BOCA-OCULTO" (-50 -50) (-50 -92.426))
   ("L" "BOCA-OCULTO" (50 50) (50 7.574))
   ("L" "BOCA-OCULTO" (102.94 102.94) (102.94 60.513))
   ("L" "BOCA-OCULTO" (202.94 202.94) (202.94 160.513))
   ("L" "BOCA-EIXO" (0 84.853) (0 -98.995))))
  (list "BTTC 1,20 - BEAA 32" "BEAA45_BTTC120_PL"
   '(("P" "BOCA-CONCRETO" (-290.974 -290.974) (285.318 285.318) (313.602 257.033) (-262.69 -319.259))
   ("P" "BOCA-CONCRETO" (-262.69 -319.259) (-408.362 -719.489) (-374.899 -686.026) (-229.227 -285.796))
   ("P" "BOCA-CONCRETO" (313.602 257.033) (406.777 95.65) (392.136 81.009) (298.961 242.392))
   ("P" "BOCA-SOLEIRA" (-298.046 -298.046) (292.389 292.389) (320.673 264.104) (406.777 95.65) (413.848 88.579) (-401.291 -726.56) (-408.362 -719.489) (-269.761 -326.33))
   ("L" "BOCA-OCULTO" (-237.941 -237.941) (-237.941 -294.51))
   ("L" "BOCA-OCULTO" (-117.941 -117.941) (-117.941 -174.51))
   ("L" "BOCA-OCULTO" (-60 -60) (-60 -116.569))
   ("L" "BOCA-OCULTO" (60 60) (60 3.431))
   ("L" "BOCA-OCULTO" (117.941 117.941) (117.941 61.373))
   ("L" "BOCA-OCULTO" (237.941 237.941) (237.941 181.373))
   ("L" "BOCA-EIXO" (0 84.853) (0 -113.137))))
  (list "BTTC 1,50 - BEAA 33" "BEAA45_BTTC150_PL"
   '(("P" "BOCA-CONCRETO" (-348.957 -348.957) (336.936 336.936) (372.292 301.581) (-313.602 -384.313))
   ("P" "BOCA-CONCRETO" (-313.602 -384.313) (-524.017 -962.423) (-490.554 -928.96) (-280.139 -350.849))
   ("P" "BOCA-CONCRETO" (372.292 301.581) (506.878 68.471) (492.237 53.83) (357.651 286.94))
   ("P" "BOCA-SOLEIRA" (-356.028 -356.028) (344.007 344.007) (379.363 308.652) (506.878 68.471) (513.949 61.4) (-516.946 -969.494) (-524.017 -962.423) (-320.673 -391.384))
   ("L" "BOCA-OCULTO" (-286.732 -286.732) (-286.732 -357.442))
   ("L" "BOCA-OCULTO" (-136.732 -136.732) (-136.732 -207.442))
   ("L" "BOCA-OCULTO" (-75 -75) (-75 -145.711))
   ("L" "BOCA-OCULTO" (75 75) (75 4.289))
   ("L" "BOCA-OCULTO" (136.732 136.732) (136.732 66.021))
   ("L" "BOCA-OCULTO" (286.732 286.732) (286.732 216.021))
   ("L" "BOCA-EIXO" (0 84.853) (0 -127.279))))
  (list "BTTC 2,00 - EXTRAPOLADO" "BEAA45_BTTC200_PL"
   '(("P" "BOCA-CONCRETO" (-455.73 -455.73) (440.174 440.174) (486.136 394.212) (-409.768 -501.692))
   ("P" "BOCA-CONCRETO" (-409.768 -501.692) (-688.973 -1268.801) (-647.144 -1226.972) (-367.939 -459.863))
   ("P" "BOCA-CONCRETO" (486.136 394.212) (664.721 84.893) (646.42 66.592) (467.835 375.911))
   ("P" "BOCA-SOLEIRA" (-462.801 -462.801) (447.245 447.245) (493.207 401.283) (664.721 84.893) (671.792 77.822) (-681.902 -1275.872) (-688.973 -1268.801) (-416.839 -508.763))
   ("L" "BOCA-OCULTO" (-372.999 -372.999) (-372.999 -464.923))
   ("L" "BOCA-OCULTO" (-172.999 -172.999) (-172.999 -264.923))
   ("L" "BOCA-OCULTO" (-100 -100) (-100 -191.924))
   ("L" "BOCA-OCULTO" (100 100) (100 8.076))
   ("L" "BOCA-OCULTO" (172.999 172.999) (172.999 81.075))
   ("L" "BOCA-OCULTO" (372.999 372.999) (372.999 281.075))
   ("L" "BOCA-EIXO" (0 84.853) (0 -148.492))))
  (list "BTTC 2,50 - EXTRAPOLADO" "BEAA45_BTTC250_PL"
   '(("P" "BOCA-CONCRETO" (-561.796 -561.796) (541.29 541.29) (601.394 481.186) (-501.692 -621.9))
   ("P" "BOCA-CONCRETO" (-501.692 -621.9) (-853.733 -1589.124) (-811.904 -1547.295) (-459.863 -580.071))
   ("P" "BOCA-CONCRETO" (601.394 481.186) (826.567 91.176) (808.266 72.875) (583.093 462.885))
   ("P" "BOCA-SOLEIRA" (-568.867 -568.867) (548.361 548.361) (608.465 488.257) (826.567 91.176) (833.638 84.105) (-846.662 -1596.195) (-853.733 -1589.124) (-508.763 -628.971))
   ("L" "BOCA-OCULTO" (-457.852 -457.852) (-457.852 -578.06))
   ("L" "BOCA-OCULTO" (-207.852 -207.852) (-207.852 -328.06))
   ("L" "BOCA-OCULTO" (-125 -125) (-125 -245.208))
   ("L" "BOCA-OCULTO" (125 125) (125 4.792))
   ("L" "BOCA-OCULTO" (207.852 207.852) (207.852 87.643))
   ("L" "BOCA-OCULTO" (457.852 457.852) (457.852 337.643))
   ("L" "BOCA-EIXO" (0 84.853) (0 -176.777))))
  (list "BTTC 3,00 - EXTRAPOLADO" "BEAA45_BTTC300_PL"
   '(("P" "BOCA-CONCRETO" (-667.509 -667.509) (643.467 643.467) (714.178 572.756) (-596.798 -738.219))
   ("P" "BOCA-CONCRETO" (-596.798 -738.219) (-1017.628 -1894.441) (-967.433 -1844.246) (-546.603 -688.025))
   ("P" "BOCA-CONCRETO" (714.178 572.756) (983.35 106.537) (961.388 84.576) (692.216 550.795))
   ("P" "BOCA-SOLEIRA" (-674.58 -674.58) (650.538 650.538) (721.249 579.828) (983.35 106.537) (990.421 99.466) (-1010.557 -1901.512) (-1017.628 -1894.441) (-603.869 -745.291))
   ("L" "BOCA-OCULTO" (-543.058 -543.058) (-543.058 -684.479))
   ("L" "BOCA-OCULTO" (-243.058 -243.058) (-243.058 -384.479))
   ("L" "BOCA-OCULTO" (-150 -150) (-150 -291.421))
   ("L" "BOCA-OCULTO" (150 150) (150 8.579))
   ("L" "BOCA-OCULTO" (243.058 243.058) (243.058 101.637))
   ("L" "BOCA-OCULTO" (543.058 543.058) (543.058 401.637))
   ("L" "BOCA-EIXO" (0 84.853) (0 -197.99))))
 ))
 (list "BOCA_BEAA45_FRONTAL" (list
  (list "BSTC 1,00 - BEAA 25" "BEAA45_BSTC100_FR"
   '(("P" "BOCA-CONCRETO" (-102 0) (163 0) (163 142) (-102 142))
   ("E" "BOCA-CONCRETO" (-0.289 50) 70.711 50)
   ("P" "BOCA-CONCRETO" (-102 0) (-102 142) (-455.844 25) (-455.844 0))
   ("L" "BOCA-CONCRETO" (-408.52 0) (-408.52 25))
   ("P" "BOCA-CONCRETO" (163 0) (163 142) (118.788 25) (118.788 0))
   ("L" "BOCA-CONCRETO" (98.083 0) (98.083 25))
   ("P" "BOCA-SOLEIRA" (-455.844 0) (173 0) (173 -65) (-455.844 -65))
   ("L" "BOCA-OCULTO" (-455.844 -25) (173 -25))
   ("P" "BOCA-SOLEIRA" (-455.844 -65) (173 -65) (173 -70) (-455.844 -70))))
  (list "BSTC 1,20 - BEAA 26" "BEAA45_BSTC120_FR"
   '(("P" "BOCA-CONCRETO" (-119.5 0) (195.5 0) (195.5 163) (-119.5 163))
   ("E" "BOCA-CONCRETO" (0.353 60) 84.853 60)
   ("P" "BOCA-CONCRETO" (-119.5 0) (-119.5 163) (-505.511 30) (-505.511 0))
   ("L" "BOCA-CONCRETO" (-458.187 0) (-458.187 30))
   ("P" "BOCA-CONCRETO" (195.5 0) (195.5 163) (147.269 30) (147.269 0))
   ("L" "BOCA-CONCRETO" (126.564 0) (126.564 30))
   ("P" "BOCA-SOLEIRA" (-505.511 0) (205.5 0) (205.5 -65) (-505.511 -65))
   ("L" "BOCA-OCULTO" (-505.511 -25) (205.5 -25))
   ("P" "BOCA-SOLEIRA" (-505.511 -65) (205.5 -65) (205.5 -70) (-505.511 -70))))
  (list "BSTC 1,50 - BEAA 27" "BEAA45_BSTC150_FR"
   '(("P" "BOCA-CONCRETO" (-149 0) (231 0) (231 194) (-149 194))
   ("E" "BOCA-CONCRETO" (0.066 75) 106.066 75)
   ("P" "BOCA-CONCRETO" (-149 0) (-149 194) (-706.572 35) (-706.572 0))
   ("L" "BOCA-CONCRETO" (-659.248 0) (-659.248 35))
   ("P" "BOCA-CONCRETO" (231 0) (231 194) (161.333 35) (161.333 0))
   ("L" "BOCA-CONCRETO" (140.628 0) (140.628 35))
   ("P" "BOCA-SOLEIRA" (-706.572 0) (241 0) (241 -70) (-706.572 -70))
   ("L" "BOCA-OCULTO" (-706.572 -30) (241 -30))
   ("P" "BOCA-SOLEIRA" (-706.572 -70) (241 -70) (241 -75) (-706.572 -75))))
  (list "BSTC 2,00 - EXTRAPOLADO" "BEAA45_BSTC200_FR"
   '(("P" "BOCA-CONCRETO" (-200.5 0) (306.5 0) (306.5 244) (-200.5 244))
   ("E" "BOCA-CONCRETO" (-0.079 100) 141.421 100)
   ("P" "BOCA-CONCRETO" (-200.5 0) (-200.5 244) (-940.355 45) (-940.355 0))
   ("L" "BOCA-CONCRETO" (-881.2 0) (-881.2 45))
   ("P" "BOCA-CONCRETO" (306.5 0) (306.5 244) (214.058 45) (214.058 0))
   ("L" "BOCA-CONCRETO" (188.176 0) (188.176 45))
   ("P" "BOCA-SOLEIRA" (-940.355 0) (316.5 0) (316.5 -80) (-940.355 -80))
   ("L" "BOCA-OCULTO" (-940.355 -35) (316.5 -35))
   ("P" "BOCA-SOLEIRA" (-940.355 -80) (316.5 -80) (316.5 -85) (-940.355 -85))))
  (list "BSTC 2,50 - EXTRAPOLADO" "BEAA45_BSTC250_FR"
   '(("P" "BOCA-CONCRETO" (-247 0) (387 0) (387 294) (-247 294))
   ("E" "BOCA-CONCRETO" (-0.223 125) 176.777 125)
   ("P" "BOCA-CONCRETO" (-247 0) (-247 294) (-1179.861 60) (-1179.861 0))
   ("L" "BOCA-CONCRETO" (-1120.705 0) (-1120.705 60))
   ("P" "BOCA-CONCRETO" (387 0) (387 294) (270.442 60) (270.442 0))
   ("L" "BOCA-CONCRETO" (244.56 0) (244.56 60))
   ("P" "BOCA-SOLEIRA" (-1179.861 0) (397 0) (397 -90) (-1179.861 -90))
   ("L" "BOCA-OCULTO" (-1179.861 -40) (397 -40))
   ("P" "BOCA-SOLEIRA" (-1179.861 -90) (397 -90) (397 -95) (-1179.861 -95))))
  (list "BSTC 3,00 - EXTRAPOLADO" "BEAA45_BSTC300_FR"
   '(("P" "BOCA-CONCRETO" (-298 0) (462 0) (462 344) (-298 344))
   ("E" "BOCA-CONCRETO" (0.132 150) 212.132 150)
   ("P" "BOCA-CONCRETO" (-298 0) (-298 344) (-1413.144 70) (-1413.144 0))
   ("L" "BOCA-CONCRETO" (-1342.158 0) (-1342.158 70))
   ("P" "BOCA-CONCRETO" (462 0) (462 344) (322.666 70) (322.666 0))
   ("L" "BOCA-CONCRETO" (291.608 0) (291.608 70))
   ("P" "BOCA-SOLEIRA" (-1413.144 0) (472 0) (472 -95) (-1413.144 -95))
   ("L" "BOCA-OCULTO" (-1413.144 -40) (472 -40))
   ("P" "BOCA-SOLEIRA" (-1413.144 -95) (472 -95) (472 -100) (-1413.144 -100))))
  (list "BDTC 1,00 - BEAA 28" "BEAA45_BDTC100_FR"
   '(("P" "BOCA-CONCRETO" (-210 0) (275 0) (275 142) (-210 142))
   ("E" "BOCA-CONCRETO" (-108.289 50) 70.711 50)
   ("E" "BOCA-CONCRETO" (108.289 50) 70.711 50)
   ("P" "BOCA-CONCRETO" (-210 0) (-210 142) (-563.844 30) (-563.844 0))
   ("L" "BOCA-CONCRETO" (-516.52 0) (-516.52 30))
   ("P" "BOCA-CONCRETO" (275 0) (275 142) (230.788 30) (230.788 0))
   ("L" "BOCA-CONCRETO" (210.083 0) (210.083 30))
   ("P" "BOCA-SOLEIRA" (-563.844 0) (285 0) (285 -65) (-563.844 -65))
   ("L" "BOCA-OCULTO" (-563.844 -25) (285 -25))
   ("P" "BOCA-SOLEIRA" (-563.844 -65) (285 -65) (285 -70) (-563.844 -70))))
  (list "BDTC 1,20 - BEAA 29" "BEAA45_BDTC120_FR"
   '(("P" "BOCA-CONCRETO" (-245.5 0) (319.5 0) (319.5 163) (-245.5 163))
   ("E" "BOCA-CONCRETO" (-125.647 60) 84.853 60)
   ("E" "BOCA-CONCRETO" (125.647 60) 84.853 60)
   ("P" "BOCA-CONCRETO" (-245.5 0) (-245.5 163) (-631.511 35) (-631.511 0))
   ("L" "BOCA-CONCRETO" (-584.187 0) (-584.187 35))
   ("P" "BOCA-CONCRETO" (319.5 0) (319.5 163) (271.269 35) (271.269 0))
   ("L" "BOCA-CONCRETO" (250.564 0) (250.564 35))
   ("P" "BOCA-SOLEIRA" (-631.511 0) (329.5 0) (329.5 -65) (-631.511 -65))
   ("L" "BOCA-OCULTO" (-631.511 -25) (329.5 -25))
   ("P" "BOCA-SOLEIRA" (-631.511 -65) (329.5 -65) (329.5 -70) (-631.511 -70))))
  (list "BDTC 1,50 - BEAA 30" "BEAA45_BDTC150_FR"
   '(("P" "BOCA-CONCRETO" (-294 0) (376 0) (376 194) (-294 194))
   ("E" "BOCA-CONCRETO" (-149.934 75) 106.066 75)
   ("E" "BOCA-CONCRETO" (149.934 75) 106.066 75)
   ("P" "BOCA-CONCRETO" (-294 0) (-294 194) (-851.572 35) (-851.572 0))
   ("L" "BOCA-CONCRETO" (-804.248 0) (-804.248 35))
   ("P" "BOCA-CONCRETO" (376 0) (376 194) (306.333 35) (306.333 0))
   ("L" "BOCA-CONCRETO" (285.628 0) (285.628 35))
   ("P" "BOCA-SOLEIRA" (-851.572 0) (386 0) (386 -70) (-851.572 -70))
   ("L" "BOCA-OCULTO" (-851.572 -30) (386 -30))
   ("P" "BOCA-SOLEIRA" (-851.572 -70) (386 -70) (386 -75) (-851.572 -75))))
  (list "BDTC 2,00 - EXTRAPOLADO" "BEAA45_BDTC200_FR"
   '(("P" "BOCA-CONCRETO" (-386.5 0) (492.5 0) (492.5 244) (-386.5 244))
   ("E" "BOCA-CONCRETO" (-193.079 100) 141.421 100)
   ("E" "BOCA-CONCRETO" (193.079 100) 141.421 100)
   ("P" "BOCA-CONCRETO" (-386.5 0) (-386.5 244) (-1126.355 45) (-1126.355 0))
   ("L" "BOCA-CONCRETO" (-1067.2 0) (-1067.2 45))
   ("P" "BOCA-CONCRETO" (492.5 0) (492.5 244) (400.058 45) (400.058 0))
   ("L" "BOCA-CONCRETO" (374.176 0) (374.176 45))
   ("P" "BOCA-SOLEIRA" (-1126.355 0) (502.5 0) (502.5 -80) (-1126.355 -80))
   ("L" "BOCA-OCULTO" (-1126.355 -35) (502.5 -35))
   ("P" "BOCA-SOLEIRA" (-1126.355 -80) (502.5 -80) (502.5 -85) (-1126.355 -85))))
  (list "BDTC 2,50 - EXTRAPOLADO" "BEAA45_BDTC250_FR"
   '(("P" "BOCA-CONCRETO" (-474 0) (614 0) (614 294) (-474 294))
   ("E" "BOCA-CONCRETO" (-235.223 125) 176.777 125)
   ("E" "BOCA-CONCRETO" (235.223 125) 176.777 125)
   ("P" "BOCA-CONCRETO" (-474 0) (-474 294) (-1406.861 60) (-1406.861 0))
   ("L" "BOCA-CONCRETO" (-1347.705 0) (-1347.705 60))
   ("P" "BOCA-CONCRETO" (614 0) (614 294) (497.442 60) (497.442 0))
   ("L" "BOCA-CONCRETO" (471.56 0) (471.56 60))
   ("P" "BOCA-SOLEIRA" (-1406.861 0) (624 0) (624 -90) (-1406.861 -90))
   ("L" "BOCA-OCULTO" (-1406.861 -40) (624 -40))
   ("P" "BOCA-SOLEIRA" (-1406.861 -90) (624 -90) (624 -95) (-1406.861 -95))))
  (list "BDTC 3,00 - EXTRAPOLADO" "BEAA45_BDTC300_FR"
   '(("P" "BOCA-CONCRETO" (-566 0) (730 0) (730 344) (-566 344))
   ("E" "BOCA-CONCRETO" (-277.868 150) 212.132 150)
   ("E" "BOCA-CONCRETO" (277.868 150) 212.132 150)
   ("P" "BOCA-CONCRETO" (-566 0) (-566 344) (-1681.144 70) (-1681.144 0))
   ("L" "BOCA-CONCRETO" (-1610.158 0) (-1610.158 70))
   ("P" "BOCA-CONCRETO" (730 0) (730 344) (590.666 70) (590.666 0))
   ("L" "BOCA-CONCRETO" (559.608 0) (559.608 70))
   ("P" "BOCA-SOLEIRA" (-1681.144 0) (740 0) (740 -95) (-1681.144 -95))
   ("L" "BOCA-OCULTO" (-1681.144 -40) (740 -40))
   ("P" "BOCA-SOLEIRA" (-1681.144 -95) (740 -95) (740 -100) (-1681.144 -100))))
  (list "BTTC 1,00 - BEAA 31" "BEAA45_BTTC100_FR"
   '(("P" "BOCA-CONCRETO" (-318 0) (382 0) (382 142) (-318 142))
   ("E" "BOCA-CONCRETO" (-216.289 50) 70.711 50)
   ("E" "BOCA-CONCRETO" (0 50) 70.711 50)
   ("E" "BOCA-CONCRETO" (216.289 50) 70.711 50)
   ("P" "BOCA-CONCRETO" (-318 0) (-318 142) (-671.844 35) (-671.844 0))
   ("L" "BOCA-CONCRETO" (-624.52 0) (-624.52 35))
   ("P" "BOCA-CONCRETO" (382 0) (382 142) (337.788 35) (337.788 0))
   ("L" "BOCA-CONCRETO" (317.083 0) (317.083 35))
   ("P" "BOCA-SOLEIRA" (-671.844 0) (392 0) (392 -65) (-671.844 -65))
   ("L" "BOCA-OCULTO" (-671.844 -25) (392 -25))   ("P" "BOCA-SOLEIRA" (-671.844 -65) (392 -65) (392 -70) (-671.844 -70))))
  (list "BTTC 1,20 - BEAA 32" "BEAA45_BTTC120_FR"
   '(("P" "BOCA-CONCRETO" (-371.5 0) (443.5 0) (443.5 163) (-371.5 163))
   ("E" "BOCA-CONCRETO" (-251.647 60) 84.853 60)
   ("E" "BOCA-CONCRETO" (0 60) 84.853 60)
   ("E" "BOCA-CONCRETO" (251.647 60) 84.853 60)
   ("P" "BOCA-CONCRETO" (-371.5 0) (-371.5 163) (-757.511 40) (-757.511 0))
   ("L" "BOCA-CONCRETO" (-710.187 0) (-710.187 40))
   ("P" "BOCA-CONCRETO" (443.5 0) (443.5 163) (395.269 40) (395.269 0))
   ("L" "BOCA-CONCRETO" (374.564 0) (374.564 40))
   ("P" "BOCA-SOLEIRA" (-757.511 0) (453.5 0) (453.5 -65) (-757.511 -65))
   ("L" "BOCA-OCULTO" (-757.511 -25) (453.5 -25))
   ("P" "BOCA-SOLEIRA" (-757.511 -65) (453.5 -65) (453.5 -70) (-757.511 -70))))
  (list "BTTC 1,50 - BEAA 33" "BEAA45_BTTC150_FR"
   '(("P" "BOCA-CONCRETO" (-443.5 0) (526.5 0) (526.5 194) (-443.5 194))
   ("E" "BOCA-CONCRETO" (-299.434 75) 106.066 75)
   ("E" "BOCA-CONCRETO" (0 75) 106.066 75)
   ("E" "BOCA-CONCRETO" (299.434 75) 106.066 75)
   ("P" "BOCA-CONCRETO" (-443.5 0) (-443.5 194) (-1001.072 40) (-1001.072 0))
   ("L" "BOCA-CONCRETO" (-953.748 0) (-953.748 40))
   ("P" "BOCA-CONCRETO" (526.5 0) (526.5 194) (456.833 40) (456.833 0))
   ("L" "BOCA-CONCRETO" (436.128 0) (436.128 40))
   ("P" "BOCA-SOLEIRA" (-1001.072 0) (536.5 0) (536.5 -70) (-1001.072 -70))
   ("L" "BOCA-OCULTO" (-1001.072 -30) (536.5 -30))
   ("P" "BOCA-SOLEIRA" (-1001.072 -70) (536.5 -70) (536.5 -75) (-1001.072 -75))))
  (list "BTTC 2,00 - EXTRAPOLADO" "BEAA45_BTTC200_FR"
   '(("P" "BOCA-CONCRETO" (-579.5 0) (687.5 0) (687.5 244) (-579.5 244))
   ("E" "BOCA-CONCRETO" (-386.079 100) 141.421 100)
   ("E" "BOCA-CONCRETO" (0 100) 141.421 100)
   ("E" "BOCA-CONCRETO" (386.079 100) 141.421 100)
   ("P" "BOCA-CONCRETO" (-579.5 0) (-579.5 244) (-1319.355 55) (-1319.355 0))
   ("L" "BOCA-CONCRETO" (-1260.2 0) (-1260.2 55))
   ("P" "BOCA-CONCRETO" (687.5 0) (687.5 244) (595.058 55) (595.058 0))
   ("L" "BOCA-CONCRETO" (569.176 0) (569.176 55))
   ("P" "BOCA-SOLEIRA" (-1319.355 0) (697.5 0) (697.5 -80) (-1319.355 -80))
   ("L" "BOCA-OCULTO" (-1319.355 -35) (697.5 -35))
   ("P" "BOCA-SOLEIRA" (-1319.355 -80) (697.5 -80) (697.5 -85) (-1319.355 -85))))
  (list "BTTC 2,50 - EXTRAPOLADO" "BEAA45_BTTC250_FR"
   '(("P" "BOCA-CONCRETO" (-709.5 0) (850.5 0) (850.5 294) (-709.5 294))
   ("E" "BOCA-CONCRETO" (-470.723 125) 176.777 125)
   ("E" "BOCA-CONCRETO" (0 125) 176.777 125)
   ("E" "BOCA-CONCRETO" (470.723 125) 176.777 125)
   ("P" "BOCA-CONCRETO" (-709.5 0) (-709.5 294) (-1642.361 65) (-1642.361 0))
   ("L" "BOCA-CONCRETO" (-1583.205 0) (-1583.205 65))
   ("P" "BOCA-CONCRETO" (850.5 0) (850.5 294) (733.942 65) (733.942 0))
   ("L" "BOCA-CONCRETO" (708.06 0) (708.06 65))
   ("P" "BOCA-SOLEIRA" (-1642.361 0) (860.5 0) (860.5 -90) (-1642.361 -90))
   ("L" "BOCA-OCULTO" (-1642.361 -40) (860.5 -40))
   ("P" "BOCA-SOLEIRA" (-1642.361 -90) (860.5 -90) (860.5 -95) (-1642.361 -95))))
  (list "BTTC 3,00 - EXTRAPOLADO" "BEAA45_BTTC300_FR"
   '(("P" "BOCA-CONCRETO" (-844 0) (1010 0) (1010 344) (-844 344))
   ("E" "BOCA-CONCRETO" (-555.868 150) 212.132 150)
   ("E" "BOCA-CONCRETO" (0 150) 212.132 150)
   ("E" "BOCA-CONCRETO" (555.868 150) 212.132 150)
   ("P" "BOCA-CONCRETO" (-844 0) (-844 344) (-1959.144 80) (-1959.144 0))
   ("L" "BOCA-CONCRETO" (-1888.158 0) (-1888.158 80))
   ("P" "BOCA-CONCRETO" (1010 0) (1010 344) (870.666 80) (870.666 0))
   ("L" "BOCA-CONCRETO" (839.608 0) (839.608 80))
   ("P" "BOCA-SOLEIRA" (-1959.144 0) (1020 0) (1020 -95) (-1959.144 -95))
   ("L" "BOCA-OCULTO" (-1959.144 -40) (1020 -40))
   ("P" "BOCA-SOLEIRA" (-1959.144 -95) (1020 -95) (1020 -100) (-1959.144 -100))))
 ))
))
(princ "\nBocasBueiroDNIT carregado: BOCASTESTE / BOCASDNIT / BOCASBASE")
(princ)


;;; 18 templates extraidos do DWG atualizado; coordenadas em cm.
(setq *bc:cadastro* (list
(list "BSTC 1.00 - TEMPLATE" "CAD_BSTC100_V2_PL" '(
("C" 0 7 (50 0) (50 -30))
("C" 0 7 (-50 0) (-50 -30))
("C" 1 256 (85 0) (85 -30) (-85 -30) (-85 0))
("C" 0 256 (-85 0) (-95 0) (-95 -27.64416826) (-168.5088059 -175))
("C" 0 256 (85 0) (95 0) (95 -27.64416826) (168.5088059 -175))
("C" 0 256 (168.5088059 -175) (168.5088059 -205) (-168.5088059 -205) (-168.5088059 -175))
("C" 0 256 (-85 -30) (-162.33244914 -185.0207111) (-145 -195) (-50 -30))
("C" 0 256 (50 -30) (145 -195) (162.27080103 -185.05620547) (85 -30))
("C" 0 7 (168.5088059 -175) (-168.5088059 -175))
("C" 0 7 (-58 0) (-58 -30))
("C" 0 7 (58 0) (58 -30))))
(list "BSTC 1.20 - TEMPLATE" "CAD_BSTC120_V2_PL" '(
("C" 0 7 (-178.5088059 -175) (178.5088059 -175))
("C" 0 256 (-178.5088059 -175) (-178.5088059 -205) (178.5088059 -205) (178.5088059 -175))
("C" 0 256 (-95 0) (-105 0) (-105 -27.64416827) (-178.5088059 -175))
("C" 0 256 (-60 -30) (-155 -195) (-172.27080103 -185.05620547) (-95 -30))
("C" 1 256 (-95 0) (-95 -30) (95 -30) (95 0))
("C" 0 7 (-68 0) (-68 -30))
("C" 0 7 (-60 0) (-60 -30))
("C" 0 256 (95 -30) (172.33244914 -185.0207111) (155 -195) (60 -30))
("C" 0 7 (60 0) (60 -30))
("C" 0 7 (68 0) (68 -30))
("C" 0 256 (95 0) (105 0) (105 -27.64416827) (178.5088059 -175))))
(list "BSTC 1.50 - TEMPLATE" "CAD_BSTC150_V2_PL" '(
("C" 0 7 (-193.5088059 -175) (193.5088059 -175))
("C" 0 256 (-193.5088059 -175) (-193.5088059 -205) (193.5088059 -205) (193.5088059 -175))
("C" 0 256 (-110 0) (-120 0) (-120 -27.64416827) (-193.5088059 -175))
("C" 0 256 (-75 -30) (-170 -195) (-187.27080103 -185.05620547) (-110 -30))
("C" 1 256 (-110 0) (-110 -30) (110 -30) (110 0))
("C" 0 7 (-83 0) (-83 -30))
("C" 0 7 (-75 0) (-75 -30))
("C" 0 256 (110 -30) (187.33244914 -185.0207111) (170 -195) (75 -30))
("C" 0 7 (75 0) (75 -30))
("C" 0 7 (83 0) (83 -30))
("C" 0 256 (110 0) (120 0) (120 -27.64416827) (193.5088059 -175))))
(list "BSTC 2.00 - TEMPLATE" "CAD_BSTC200_V2_PL" '(
("C" 0 7 (-218.5088059 -175) (218.5088059 -175))
("C" 0 256 (-218.5088059 -175) (-218.5088059 -205) (218.5088059 -205) (218.5088059 -175))
("C" 0 256 (-135 0) (-145 0) (-145 -27.64416827) (-218.5088059 -175))
("C" 0 256 (-100 -30) (-195 -195) (-212.27080103 -185.05620547) (-135 -30))
("C" 1 256 (-135 0) (-135 -30) (135 -30) (135 0))
("C" 0 7 (-108 0) (-108 -30))
("C" 0 7 (-100 0) (-100 -30))
("C" 0 256 (135 -30) (212.33244914 -185.0207111) (195 -195) (100 -30))
("C" 0 7 (100 0) (100 -30))
("C" 0 7 (108 0) (108 -30))
("C" 0 256 (135 0) (145 0) (145 -27.64416827) (218.5088059 -175))))
(list "BSTC 2.50 - TEMPLATE" "CAD_BSTC250_V2_PL" '(
("C" 0 7 (-243.5088059 -175) (243.5088059 -175))
("C" 0 256 (-243.5088059 -175) (-243.5088059 -205) (243.5088059 -205) (243.5088059 -175))
("C" 0 256 (-160 0) (-170 0) (-170 -27.64416827) (-243.5088059 -175))
("C" 0 256 (-125 -30) (-220 -195) (-237.27080103 -185.05620547) (-160 -30))
("C" 1 256 (-160 0) (-160 -30) (160 -30) (160 0))
("C" 0 7 (-133 0) (-133 -30))
("C" 0 7 (-125 0) (-125 -30))
("C" 0 256 (160 -30) (237.33244914 -185.0207111) (220 -195) (125 -30))
("C" 0 7 (125 0) (125 -30))
("C" 0 7 (133 0) (133 -30))
("C" 0 256 (160 0) (170 0) (170 -27.64416827) (243.5088059 -175))))
(list "BSTC 3.00 - TEMPLATE" "CAD_BSTC300_V2_PL" '(
("C" 0 7 (-268.5088059 -175) (268.5088059 -175))
("C" 0 256 (-268.5088059 -175) (-268.5088059 -205) (268.5088059 -205) (268.5088059 -175))
("C" 0 256 (-185 0) (-195 0) (-195 -27.64416827) (-268.5088059 -175))
("C" 0 256 (-150 -30) (-245 -195) (-262.27080103 -185.05620547) (-185 -30))
("C" 1 256 (-185 0) (-185 -30) (185 -30) (185 0))
("C" 0 7 (-158 0) (-158 -30))
("C" 0 7 (-150 0) (-150 -30))
("C" 0 256 (185 -30) (262.33244914 -185.0207111) (245 -195) (150 -30))
("C" 0 7 (150 0) (150 -30))
("C" 0 7 (158 0) (158 -30))
("C" 0 256 (185 0) (195 0) (195 -27.64416827) (268.5088059 -175))))
(list "BDTC 1.00 - TEMPLATE" "CAD_BDTC100_V2_PL" '(
("C" 0 7 (-222.5088059 -175) (222.5088059 -175))
("C" 0 256 (-222.5088059 -175) (-222.5088059 -205) (222.5088059 -205) (222.5088059 -175))
("C" 0 256 (-139 0) (-149 0) (-149 -27.64416827) (-222.5088059 -175))
("C" 0 256 (-104 -30) (-199 -195) (-216.27080103 -185.05620547) (-139 -30))
("C" 1 256 (-139 0) (-139 -30) (139 -30) (139 0))
("C" 0 7 (-112 0) (-112 -30))
("C" 0 7 (-104 0) (-104 -30))
("C" 0 7 (-4 0) (-4 -30))
("C" 0 7 (4 0) (4 -30))
("C" 0 7 (104 0) (104 -30))
("C" 0 256 (139 -30) (216.33244914 -185.0207111) (199 -195) (104 -30))
("C" 0 7 (112 0) (112 -30))
("C" 0 256 (139 0) (149 0) (149 -27.64416827) (222.5088059 -175))))
(list "BDTC 1.20 - TEMPLATE" "CAD_BDTC120_V2_PL" '(
("C" 0 7 (-242.5088059 -175) (242.5088059 -175))
("C" 0 256 (-242.5088059 -175) (-242.5088059 -205) (242.5088059 -205) (242.5088059 -175))
("C" 0 256 (-159 0) (-169 0) (-169 -27.64416826) (-242.5088059 -175))
("C" 0 256 (-124 -30) (-219 -195) (-236.27080103 -185.05620547) (-159 -30))
("C" 1 256 (-159 0) (-159 -30) (159 -30) (159 0))
("C" 0 7 (-132 0) (-132 -30))
("C" 0 7 (-124 0) (-124 -30))
("C" 0 7 (-4 0) (-4 -30))
("C" 0 7 (4 0) (4 -30))
("C" 0 7 (124 0) (124 -30))
("C" 0 256 (159 -30) (236.33244914 -185.0207111) (219 -195) (124 -30))
("C" 0 7 (132 0) (132 -30))
("C" 0 256 (159 0) (169 0) (169 -27.64416826) (242.5088059 -175))))
(list "BDTC 1.50 - TEMPLATE" "CAD_BDTC150_V2_PL" '(
("C" 0 7 (-272.5088059 -175) (272.5088059 -175))
("C" 0 256 (-272.5088059 -175) (-272.5088059 -205) (272.5088059 -205) (272.5088059 -175))
("C" 0 256 (-189 0) (-199 0) (-199 -27.64416827) (-272.5088059 -175))
("C" 0 256 (-154 -30) (-249 -195) (-266.27080103 -185.05620547) (-189 -30))
("C" 1 256 (-189 0) (-189 -30) (189 -30) (189 0))
("C" 0 7 (-162 0) (-162 -30))
("C" 0 7 (-154 0) (-154 -30))
("C" 0 7 (-4 0) (-4 -30))
("C" 0 7 (4 0) (4 -30))
("C" 0 7 (154 0) (154 -30))
("C" 0 256 (189 -30) (266.33244914 -185.0207111) (249 -195) (154 -30))
("C" 0 7 (162 0) (162 -30))
("C" 0 256 (189 0) (199 0) (199 -27.64416826) (272.5088059 -175))))
(list "BDTC 2.00 - TEMPLATE" "CAD_BDTC200_V2_PL" '(
("C" 0 7 (-322.5088059 -175) (322.5088059 -175))
("C" 0 256 (-322.5088059 -175) (-322.5088059 -205) (322.5088059 -205) (322.5088059 -175))
("C" 0 256 (-239 0) (-249 0) (-249 -27.64416827) (-322.5088059 -175))
("C" 0 256 (-204 -30) (-299 -195) (-316.27080103 -185.05620547) (-239 -30))
("C" 1 256 (-239 0) (-239 -30) (239 -30) (239 0))
("C" 0 7 (-212 0) (-212 -30))
("C" 0 7 (-204 0) (-204 -30))
("C" 0 7 (-4 0) (-4 -30))
("C" 0 7 (4 0) (4 -30))
("C" 0 7 (204 0) (204 -30))
("C" 0 256 (239 -30) (316.33244914 -185.0207111) (299 -195) (204 -30))
("C" 0 7 (212 0) (212 -30))
("C" 0 256 (239 0) (249 0) (249 -27.64416827) (322.5088059 -175))))
(list "BDTC 2.50 - TEMPLATE" "CAD_BDTC250_V2_PL" '(
("C" 0 7 (-372.5088059 -175) (372.5088059 -175))
("C" 0 256 (-372.5088059 -175) (-372.5088059 -205) (372.5088059 -205) (372.5088059 -175))
("C" 0 256 (-289 0) (-299 0) (-299 -27.64416827) (-372.5088059 -175))
("C" 0 256 (-254 -30) (-349 -195) (-366.27080103 -185.05620547) (-289 -30))
("C" 1 256 (-289 0) (-289 -30) (289 -30) (289 0))
("C" 0 7 (-262 0) (-262 -30))
("C" 0 7 (-254 0) (-254 -30))
("C" 0 7 (-4 0) (-4 -30))
("C" 0 7 (4 0) (4 -30))
("C" 0 7 (254 0) (254 -30))
("C" 0 256 (289 -30) (366.33244914 -185.0207111) (349 -195) (254 -30))
("C" 0 7 (262 0) (262 -30))
("C" 0 256 (289 0) (299 0) (299 -27.64416827) (372.5088059 -175))))
(list "BDTC 3.00 - TEMPLATE" "CAD_BDTC300_V2_PL" '(
("C" 0 7 (-422.5088059 -175) (422.5088059 -175))
("C" 0 256 (-422.5088059 -175) (-422.5088059 -205) (422.5088059 -205) (422.5088059 -175))
("C" 0 256 (-339 0) (-349 0) (-349 -27.64416827) (-422.5088059 -175))
("C" 0 256 (-304 -30) (-399 -195) (-416.27080103 -185.05620547) (-339 -30))
("C" 1 256 (-339 0) (-339 -30) (339 -30) (339 0))
("C" 0 7 (-312 0) (-312 -30))
("C" 0 7 (-304 0) (-304 -30))
("C" 0 7 (-4 0) (-4 -30))
("C" 0 7 (4 0) (4 -30))
("C" 0 7 (304 0) (304 -30))
("C" 0 256 (339 -30) (416.33244914 -185.0207111) (399 -195) (304 -30))
("C" 0 7 (312 0) (312 -30))
("C" 0 256 (339 0) (349 0) (349 -27.64416826) (422.5088059 -175))))
(list "BTTC 1.00 - TEMPLATE" "CAD_BTTC100_V2_PL" '(
("C" 0 256 (-276.5088059 -175) (-276.45498217 -204.58973645) (276.5088059 -205) (276.5088059 -175))
("C" 0 256 (-193 0) (-203 0) (-203 -27.64416827) (-276.5088059 -175))
("C" 0 7 (-276.5069761 -176.00593571) (276.5088059 -175))
("C" 0 256 (-158 -30) (-253 -195) (-270.27080103 -185.05620547) (-193 -30))
("C" 1 256 (-193 0) (-193 -30) (193 -30) (193 0))
("C" 0 7 (-166 0) (-166 -30))
("C" 0 7 (-158 0) (-158 -30))
("C" 0 7 (-58 0) (-58 -30))
("C" 0 7 (-50 0) (-50 -30))
("C" 0 7 (50 0) (50 -30))
("C" 0 7 (58 0) (58 -30))
("C" 0 7 (158 0) (158 -30))
("C" 0 256 (193 -30) (270.33244914 -185.0207111) (253 -195) (158 -30))
("C" 0 7 (166 0) (166 -30))
("C" 0 256 (193 0) (203 0) (203 -27.64416827) (276.5088059 -175))))
(list "BTTC 1.20 - TEMPLATE" "CAD_BTTC120_V2_PL" '(
("C" 0 7 (-306.5088059 -175) (306.5088059 -175))
("C" 0 256 (-306.5088059 -175) (-306.5088059 -205) (306.5088059 -205) (306.5088059 -175))
("C" 0 256 (-223 0) (-233 0) (-233 -27.64416827) (-306.5088059 -175))
("C" 0 256 (-188 -30) (-283 -195) (-300.27080103 -185.05620547) (-223 -30))
("C" 1 256 (-223 0) (-223 -30) (223 -30) (223 0))
("C" 0 7 (-196 0) (-196 -30))
("C" 0 7 (-188 0) (-188 -30))
("C" 0 7 (-68 0) (-68 -30))
("C" 0 7 (-60 0) (-60 -30))
("C" 0 7 (60 0) (60 -30))
("C" 0 7 (68 0) (68 -30))
("C" 0 7 (188 0) (188 -30))
("C" 0 256 (223 -30) (300.33244914 -185.0207111) (283 -195) (188 -30))
("C" 0 7 (196 0) (196 -30))
("C" 0 256 (223 0) (233 0) (233 -27.64416827) (306.5088059 -175))))
(list "BTTC 1.50 - TEMPLATE" "CAD_BTTC150_V2_PL" '(
("C" 0 7 (-351.5088059 -175) (351.5088059 -175))
("C" 0 256 (-351.5088059 -175) (-351.5088059 -205) (351.5088059 -205) (351.5088059 -175))
("C" 0 256 (-268 0) (-278 0) (-278 -27.64416827) (-351.5088059 -175))
("C" 0 256 (-233 -30) (-328 -195) (-345.27080103 -185.05620547) (-268 -30))
("C" 1 256 (-268 0) (-268 -30) (268 -30) (268 0))
("C" 0 7 (-241 0) (-241 -30))
("C" 0 7 (-233 0) (-233 -30))
("C" 0 7 (-83 0) (-83 -30))
("C" 0 7 (-75 0) (-75 -30))
("C" 0 7 (75 0) (75 -30))
("C" 0 7 (83 0) (83 -30))
("C" 0 7 (233 0) (233 -30))
("C" 0 256 (268 -30) (345.33244914 -185.0207111) (328 -195) (233 -30))
("C" 0 7 (241 0) (241 -30))
("C" 0 256 (268 0) (278 0) (278 -27.64416827) (351.5088059 -175))))
(list "BTTC 2.00 - TEMPLATE" "CAD_BTTC200_V2_PL" '(
("C" 0 7 (-426.5088059 -175) (426.5088059 -175))
("C" 0 256 (-426.5088059 -175) (-426.5088059 -205) (426.5088059 -205) (426.5088059 -175))
("C" 0 256 (-343 0) (-353 0) (-353 -27.64416827) (-426.5088059 -175))
("C" 0 256 (-308 -30) (-403 -195) (-420.27080103 -185.05620547) (-343 -30))
("C" 1 256 (-343 0) (-343 -30) (343 -30) (343 0))
("C" 0 7 (-316 0) (-316 -30))
("C" 0 7 (-308 0) (-308 -30))
("C" 0 7 (-108 0) (-108 -30))
("C" 0 7 (-100 0) (-100 -30))
("C" 0 7 (100 0) (100 -30))
("C" 0 7 (108 0) (108 -30))
("C" 0 7 (308 0) (308 -30))
("C" 0 256 (343 -30) (420.33244914 -185.0207111) (403 -195) (308 -30))
("C" 0 7 (316 0) (316 -30))
("C" 0 256 (343 0) (353 0) (353 -27.64416826) (426.5088059 -175))))
(list "BTTC 2.50 - TEMPLATE" "CAD_BTTC250_V2_PL" '(
("C" 0 7 (-501.5088059 -175) (501.5088059 -175))
("C" 0 256 (-501.5088059 -175) (-501.5088059 -205) (501.5088059 -205) (501.5088059 -175))
("C" 0 256 (-418 0) (-428 0) (-428 -27.64416827) (-501.5088059 -175))
("C" 0 256 (-383 -30) (-478 -195) (-495.27080103 -185.05620547) (-418 -30))
("C" 1 256 (-418 0) (-418 -30) (418 -30) (418 0))
("C" 0 7 (-391 0) (-391 -30))
("C" 0 7 (-383 0) (-383 -30))
("C" 0 7 (-133 0) (-133 -30))
("C" 0 7 (-125 0) (-125 -30))
("C" 0 7 (125 0) (125 -30))
("C" 0 7 (133 0) (133 -30))
("C" 0 7 (383 0) (383 -30))
("C" 0 256 (418 -30) (495.33244914 -185.0207111) (478 -195) (383 -30))
("C" 0 7 (391 0) (391 -30))
("C" 0 256 (418 0) (428 0) (428 -27.64416827) (501.5088059 -175))))
(list "BTTC 3.00 - TEMPLATE" "CAD_BTTC300_V2_PL" '(
("C" 0 7 (-576.5088059 -175) (576.5088059 -175))
("C" 0 256 (-576.5088059 -175) (-576.5088059 -205) (576.5088059 -205) (576.5088059 -175))
("C" 0 256 (-493 0) (-503 0) (-503 -27.64416826) (-576.5088059 -175))
("C" 0 256 (-458 -30) (-553 -195) (-570.27080103 -185.05620547) (-493 -30))
("C" 1 256 (-493 0) (-493 -30) (493 -30) (493 0))
("C" 0 7 (-466 0) (-466 -30))
("C" 0 7 (-458 0) (-458 -30))
("C" 0 7 (-158 0) (-158 -30))
("C" 0 7 (-150 0) (-150 -30))
("C" 0 7 (150 0) (150 -30))
("C" 0 7 (158 0) (158 -30))
("C" 0 7 (458 0) (458 -30))
("C" 0 256 (493 -30) (570.33244914 -185.0207111) (553 -195) (458 -30))
("C" 0 7 (466 0) (466 -30))
("C" 0 256 (493 0) (503 0) (503 -27.64416826) (576.5088059 -175))))
))

(defun bc:falha (msg) (prompt (strcat "\n" msg)) (exit))
(defun bc:cad-estilo (/ k nm)
  (setq k (* 100.0 (bc:esc)) nm (strcat "BC_CAD_HIDDEN_" (itoa (getvar "INSUNITS"))))
  (if (not (tblsearch "LTYPE" nm))
    (if (not (entmake (list '(0 . "LTYPE") '(100 . "AcDbSymbolTableRecord")
      '(100 . "AcDbLinetypeTableRecord") (cons 2 nm) '(70 . 0)
      '(3 . "Tracejado do template cadastro") '(72 . 65) '(73 . 2)
      (cons 40 (* k 0.375)) (cons 49 (* k 0.25)) '(74 . 0)
      (cons 49 (* k -0.125)) '(74 . 0))))
      (bc:falha "Nao foi possivel criar o tipo de linha do cadastro.")))
  (bc:camada *bc:layer* *bc:cor* "Continuous") nm)
;;; Layer e cor de toda a geometria dos blocos de cadastro (5 = blue)
(setq *bc:layer* "OBRAS PROJETADAS"
      *bc:cor*   5)
(defun bc:ent (en e / lt)
  (if (= (car en) "C")
    (progn (setq lt (bc:cad-estilo))
      (if (not (entmake (append
        (list '(0 . "LWPOLYLINE") '(100 . "AcDbEntity") (cons 8 *bc:layer*)
          (cons 62 *bc:cor*) (cons 6 (if (= (nth 2 en) 7) lt "Continuous"))
          '(48 . 0.5) '(100 . "AcDbPolyline")
          (cons 90 (length (cdddr en))) (cons 70 (cadr en)))
        (mapcar '(lambda (p) (list 10 (* e (car p)) (* e (cadr p)))) (cdddr en)))))
        (bc:falha "Falha ao criar polilinha do cadastro.")))
    (bc:ent-original en e)))
(defun bc:cad-unidades ()
  (if (not (member (getvar "INSUNITS") '(0 4 5 6)))
    (bc:falha "Use INSUNITS 6 (m), 5 (cm) ou 4 (mm)."))
  (if (= (getvar "INSUNITS") 0) (prompt "\nSem unidade: cadastro assume METROS."))
  (bc:esc))
(defun bc:cad-base (/ e st)
  (setq e (bc:cad-unidades)) (bc:cad-estilo)
  (foreach st *bc:cadastro* (bc:bloco-base (cadr st) (caddr st) e)) (princ))
(defun c:BOCASCADBASE ()
  (bc:cad-base)
  (prompt "\n18 blocos de cadastro disponiveis. Use BOCASCADASTRO para inserir.") (princ))
;;; pt e an sao relativos ao UCS; a referencia e gravada no OCS apropriado.
(defun bc:cad-inserir (nome pt an / normal vec ref)
  (setq normal (trans '(0.0 0.0 1.0) 1 0 T)
        vec (trans (list (cos an) (sin an) 0.0) 1 normal T))
  (setq ref (entmakex (list '(0 . "INSERT") '(100 . "AcDbEntity")
    (cons 8 *bc:layer*) '(100 . "AcDbBlockReference") (cons 2 nome)
    (cons 10 (trans pt 1 normal)) '(41 . 1.0) '(42 . 1.0) '(43 . 1.0)
    (cons 50 (atan (cadr vec) (car vec))) (cons 210 normal))))
  (if (null ref) (bc:falha "Falha ao inserir a boca.")) ref)
(defun c:BOCASCADASTRO (/ tp di cod pt an nome)
  (initget "BSTC BDTC BTTC")
  (setq tp (getkword "\nTipo [BSTC/BDTC/BTTC] <BSTC>: "))
  (if (null tp) (setq tp "BSTC"))
  (initget 6)
  (setq di (getreal "\nDiametro em metros [1.00/1.20/1.50/2.00/2.50/3.00] <1.00>: "))
  (if (null di) (setq di 1.0))
  (setq cod (cond ((equal di 1.0 1e-8) "100") ((equal di 1.2 1e-8) "120")
    ((equal di 1.5 1e-8) "150") ((equal di 2.0 1e-8) "200")
    ((equal di 2.5 1e-8) "250") ((equal di 3.0 1e-8) "300")))
  (if (null cod) (prompt "\nEscolha um dos seis diametros apresentados.")
    (progn (bc:cad-base)
      (setq nome (strcat "CAD_" tp cod "_V2_PL")
            pt (getpoint "\nCentro da face de chegada da boca: "))
      (if pt (progn (setq an (getangle pt "\nRotacao <0>: "))
        (if (null an) (setq an 0.0)) (bc:cad-inserir nome pt an))))) (princ))
(defun c:BOCASCADDIN ()
  (bc:bloco-dinamico "BOCA_CADASTRO_PLANTA_V2" *bc:cadastro* (bc:cad-unidades)) (princ))
;;; Integra as 18 variantes a familia BNAA em planta dos comandos originais.
(setq *bc:dados* (mapcar '(lambda (b)
  (if (= (car b) "BOCA_BNAA_PLANTA")
    (list "BOCA_BNAA_PLANTA_CAD_V2"
      (mapcar '(lambda (st / nome cad)
        (setq nome (strcat "CAD_" (substr (cadr st) 6 7) "_V2_PL")
              cad (vl-some '(lambda (item) (if (= (cadr item) nome) item)) *bc:cadastro*))
        (if cad (list (car cad) (cadr cad) (caddr cad)) st)) (cadr b))) b)) *bc:dados*))
(defun c:BOCASTESTE () (c:BOCASCADDIN))
(princ "\nCadastro v2: 18 templates. BOCASCADASTRO / BOCASCADBASE / BOCASCADDIN.")
(princ)

;;; CRIACAO DINAMICA V3 - comandos completos e verificacao do resultado.
(defun bc:dyn-validar (nome estados / doc bl rr result)
  (setq doc (vla-get-ActiveDocument (vlax-get-acad-object))
        bl (vl-catch-all-apply 'vla-Item (list (vla-get-Blocks doc) nome)))
  (if (and (not (vl-catch-all-error-p bl)) (= (vla-get-IsDynamicBlock bl) :vlax-true))
    (progn
      (setq result (vl-catch-all-apply
        '(lambda (/ props p valores nomes valido)
          (setq rr (vla-InsertBlock (vla-get-ModelSpace doc)
                     (vlax-3d-point '(0.0 0.0 0.0)) nome 1.0 1.0 1.0 0.0)
                props (vlax-invoke rr 'GetDynamicBlockProperties)
                nomes (mapcar 'car estados))
          (foreach p props
            (setq valores (vl-catch-all-apply 'vlax-get (list p 'AllowedValues)))
            (if (and (listp valores) (= (length valores) (length nomes))
                     (vl-every '(lambda (n) (member n valores)) nomes))
              (setq valido T)))
          valido)))
      (if rr (vl-catch-all-apply 'vla-Delete (list rr)))
      (and (not (vl-catch-all-error-p result)) result))))
(defun bc:dyn-check (etapa)
  (if (/= (logand 1 (getvar "CMDACTIVE")) 0)
    (bc:falha (strcat "Comando pendente em " etapa "."))))
(defun bc:dyn-preservar (nome / n outro bloc)
  (setq n 1 outro (strcat nome "_INCOMPLETO_1"))
  (while (tblsearch "BLOCK" outro)
    (setq n (1+ n) outro (strcat nome "_INCOMPLETO_" (itoa n))))
  (setq bloc (vla-Item (vla-get-Blocks (vla-get-ActiveDocument (vlax-get-acad-object))) nome))
  (vla-put-Name bloc outro)
  (prompt (strcat "\nDefinicao anterior preservada como " outro ".")))
(defun bc:bloco-dinamico (bnome estados e / *error* sv etapa st refs ss it criado resultado)
  (setq sv (mapcar '(lambda (v) (cons v (getvar v)))
             '("OSMODE" "ATTREQ" "CMDECHO" "UCSFOLLOW" "CMDDIA")))
  (defun *error* (msg)
    (if (/= (logand 1 (getvar "CMDACTIVE")) 0) (command-s))
    (if (= (getvar "BLOCKEDITOR") 1)
      (vl-catch-all-apply '(lambda () (command-s "_.BCLOSE" "_Discard"))))
    (foreach v sv (vl-catch-all-apply 'setvar (list (car v) (cdr v))))
    (prompt (strcat "\nCriacao dinamica interrompida em " etapa ": " msg
      "\nNao foi confirmada uma definicao dinamica valida. Execute BOCASCADDIN para tentar novamente."))
    (princ))
  (setq etapa "verificacao inicial")
  (cond
    ((= (getvar "BLOCKEDITOR") 1)
      (prompt "\nFeche o Editor de Blocos antes de executar BOCASCADDIN."))
    ((= (getvar "BLOCKEDITLOCK") 1)
      (prompt "\nO Editor de Blocos esta bloqueado (BLOCKEDITLOCK=1)."))
    ((bc:dyn-validar bnome estados)
      (prompt (strcat "\n" bnome " ja foi validado com " (itoa (length estados)) " estados. Use INSERT.")))
    (T
      (if (tblsearch "BLOCK" bnome) (bc:dyn-preservar bnome))
      (setvar "OSMODE" 0) (setvar "ATTREQ" 0) (setvar "CMDECHO" 0)
      (setvar "UCSFOLLOW" 0) (setvar "CMDDIA" 0)
      (setq etapa "geometrias base")
      (foreach st estados (bc:bloco-base (cadr st) (caddr st) e))
      ;; A definicao inicial ja possui geometria; nunca e apenas um POINT.
      (entmake (list '(0 . "BLOCK") (cons 2 bnome) '(70 . 0) '(8 . "0") '(10 0.0 0.0 0.0)))
      (foreach st estados
        (if (not (entmake (list '(0 . "INSERT") '(8 . "0") (cons 2 (cadr st))
          '(10 0.0 0.0 0.0) '(41 . 1.0) '(42 . 1.0) '(43 . 1.0))))
          (bc:falha "Falha ao incluir geometria.")))
      (entmake '((0 . "ENDBLK") (8 . "0")))
      (setq etapa "abertura do Editor de Blocos")
      (command "_.-BEDIT" bnome) (bc:dyn-check etapa)
      (if (/= (getvar "BLOCKEDITOR") 1) (bc:falha "Editor de Blocos nao abriu."))
      (setq refs nil)
      (foreach st estados
        (setq ss (ssget "_X" (list '(0 . "INSERT") (cons 2 (cadr st)))))
        (if (or (null ss) (/= (sslength ss) 1))
          (bc:falha (strcat "Selecao incorreta de " (cadr st))))
        (setq refs (cons (cons (car st) (ssname ss 0)) refs)))
      (setq refs (reverse refs) etapa "parametro de visibilidade")
      (command "_.BPARAMETER" "_Visibility" "_non" (list 0.0 (* e 150.0) 0.0) "1")
      (bc:dyn-check etapa)
      (setvar "BVMODE" 1)
      (foreach it refs
        (setq etapa (strcat "estado " (car it)))
        (command "_.-BVSTATE" "_New" (car it) "_Hide") (bc:dyn-check etapa)
        (command "_.BVSHOW" (cdr it) "" "_Current") (bc:dyn-check etapa))
      (setq etapa "estado inicial")
      (command "_.-BVSTATE" "_Set" (caar refs)) (bc:dyn-check etapa)
      (command "_.-BVSTATE" "_Delete" "VisibilityState0") (bc:dyn-check etapa)
      (setvar "BVMODE" 0)
      (setq etapa "salvamento")
      (command "_.BSAVE") (bc:dyn-check etapa)
      (command "_.BCLOSE") (bc:dyn-check etapa)
      (setq etapa "validacao final")
      (if (not (bc:dyn-validar bnome estados))
        (bc:falha "A propriedade dinamica nao contem todos os estados esperados."))
      (prompt (strcat "\n" bnome " criado e validado com " (itoa (length estados)) " estados. Use INSERT."))))
  (foreach v sv (setvar (car v) (cdr v)))
  (princ))
(defun c:BOCASCADDIN ()
  (bc:cad-base)
  (bc:bloco-dinamico "BOCA_CADASTRO_PLANTA_V3" *bc:cadastro* (bc:cad-unidades)) (princ))
(defun c:BOCASADDIN () (c:BOCASCADDIN))
(defun c:BOCASTESTE () (c:BOCASCADDIN))
(princ "\nCadastro v3: BOCASCADDIN cria BOCA_CADASTRO_PLANTA_V3 com validacao.")
(princ)

;;; ==========================================================================
;;; DNIT V4 - Bocas BNAA em planta conforme as tabelas do album DNIT
;;;   Tubulares : BNAA 01 a 11 (BSTC 0.60-1.50, BDTC/BTTC 1.00-1.50)
;;;   Celulares : so os quadrados das BNAA 12 a 41 (BSCC/BDCC/BTCC
;;;               1.50X1.50, 2.00X2.00, 2.50X2.50 e 3.00X3.00)
;;; A geometria e calculada pelas cotas da tabela (cm). Origem = centro da
;;; face da testa onde o bueiro chega; bueiro ao longo de +Y, alas p/ -Y.
;;; Alas a 30 graus do eixo. Substitui o cadastro: BOCASCADDIN cria o bloco
;;; dinamico BOCA_DNIT_PLANTA_V4 e BOCASCADASTRO insere uma variante.
;;; ==========================================================================
(setq *bc:c30* (cos (/ pi 6.0))
      *bc:t30* (/ (sin (/ pi 6.0)) (cos (/ pi 6.0))))

(defun bc:pl (fech cor pts) (append (list "C" fech cor) pts))
(defun bc:espelho (pts) (mapcar '(lambda (p) (list (- (car p)) (cadr p))) pts))

;;; Tubular. n = no de linhas, a = largura da testa, b = espessura da testa,
;;; c = comprimento das alas (em Y), d = d1 = d2 (testa ate o tubo),
;;; f = espessura da ala, k = borda da soleira, m = trecho vertical final
;;; da soleira, q = espaco entre tubos.
(defun bc:geo-tc (n a b c d f k m q / h mm tw po1 po2 pi1 pi2 yv xb ala w i x1 res)
  (setq n  (float n) a (float a) b (float b) c (float c) d (float d)
        f  (float f) k (float k) m (float m) q (float q)
        h  (/ a 2.0)
        mm (+ b c k)                     ; M
        tw (/ f *bc:c30*)                ; largura da ala medida em X
        po1 (list (- h) (- b))           ; face externa da ala, no pe da testa
        pi1 (list (+ (- h) tw) (- b))    ; face interna da ala, no pe da testa
        pi2 (list (- (car pi1) (* c *bc:t30*)) (- (+ b c)))
        po2 (list (- (car pi2) (* f *bc:c30*)) (+ (cadr pi2) (* f 0.5)))
        ;; borda da soleira: paralela a ala, afastada k
        yv (- (+ (- b) (* 0.5 k)) (* *bc:c30* (/ (* k (- 1.0 *bc:c30*)) 0.5)))
        xb (+ h (* k *bc:c30*) (* 0.5 (/ (+ (- b) (* 0.5 k) mm (- m)) *bc:c30*)))
        ala (list po1 po2 pi2 pi1))
  (setq res (list
    (bc:pl 1 256 (list (list (- (+ h k)) 0.0) (list (+ h k) 0.0) (list (+ h k) yv)
                       (list xb (- m mm)) (list xb (- mm)) (list (- xb) (- mm))
                       (list (- xb) (- m mm)) (list (- (+ h k)) yv)))
    (bc:pl 1 256 (list (list (- h) 0.0) (list h 0.0) (list h (- b)) (list (- h) (- b))))
    (bc:pl 1 256 ala)
    (bc:pl 1 256 (bc:espelho ala))
    ;; faces externas dos tubos extremos (referencia de x / y da tabela)
    (bc:pl 0 7 (list (list (- d h) (- b)) (list (- d h) (- (+ b c)))))
    (bc:pl 0 7 (list (list (- h d) (- b)) (list (- h d) (- (+ b c)))))))
  ;; tubos atravessando a testa (tracejado)
  (setq w (/ (- a (* 2.0 d) (* (- n 1.0) q)) n) i 0)
  (repeat (fix n)
    (setq x1  (+ (- h) d (* i (+ w q)))
          res (append res (list (bc:pl 0 7 (list (list x1 0.0) (list x1 (- b))))
                                (bc:pl 0 7 (list (list (+ x1 w) 0.0) (list (+ x1 w) (- b))))))
          i   (1+ i)))
  res)

;;; Celular. a = largura da testa, b = espessura da testa, c = comprimento
;;; das alas ate a soleira, d = largura total no topo, e = espessura da ala.
;;; Soleira final com 20 de espessura e 32 de aba para cada lado.
(defun bc:geo-cc (a b c d e / h hc mm tw xo xl xi ala)
  (setq a  (float a) b (float b) c (float c) d (float d) e (float e)
        h  (/ a 2.0)
        hc (+ b c)
        mm (+ hc 20.0)                   ; M
        tw (/ e *bc:c30*)
        xo (+ (/ d 2.0) (* hc *bc:t30*)) ; borda externa no topo da soleira
        xl (+ xo 32.0)
        xi (+ (- h) tw)                  ; face interna da ala no pe da testa
        ala (list (list (- h) (- b)) (list xi (- b))
                  (list (- xi (* (+ c 20.0) *bc:t30*)) (- mm))
                  (list (- (- h) (* (+ c 20.0) *bc:t30*)) (- mm))))
  (list
    (bc:pl 1 256 (list (list (- (/ d 2.0)) 0.0) (list (/ d 2.0) 0.0) (list xo (- hc))
                       (list xl (- hc)) (list xl (- mm)) (list (- xl) (- mm))
                       (list (- xl) (- hc)) (list (- xo) (- hc))))
    (bc:pl 1 256 (list (list (- h) 0.0) (list h 0.0) (list h (- b)) (list (- h) (- b))))
    (bc:pl 1 256 ala)
    (bc:pl 1 256 (bc:espelho ala))
    (bc:pl 0 7 (list (list xi (- b)) (list xi (- hc))))
    (bc:pl 0 7 (list (list (- xi) (- b)) (list (- xi) (- hc))))
    (bc:pl 0 7 (list (list (- xi (* c *bc:t30*)) (- hc)) (list (- (* c *bc:t30*) xi) (- hc))))))

;;; (estado bloco-base n a b c d f k m q)
(setq *bc:dnit-tc* '(
  ("BSTC 0.60 - BNAA 01" "DNIT_BSTC060_PL" 1 110 20 125 25 15 10 20 0)
  ("BSTC 0.80 - BNAA 02" "DNIT_BSTC080_PL" 1 140 25 145 30 15 10 20 0)
  ("BSTC 1.00 - BNAA 03" "DNIT_BSTC100_PL" 1 170 30 165 35 20 10 25 0)
  ("BSTC 1.20 - BNAA 04" "DNIT_BSTC120_PL" 1 200 40 180 40 20 10 25 0)
  ("BSTC 1.50 - BNAA 05" "DNIT_BSTC150_PL" 1 245 50 260 47 20 10 25 0)
  ("BDTC 1.00 - BNAA 06" "DNIT_BDTC100_PL" 2 315 30 165 31 20 10 25 30)
  ("BDTC 1.20 - BNAA 07" "DNIT_BDTC120_PL" 2 370 40 180 36 20 10 25 30)
  ("BDTC 1.50 - BNAA 08" "DNIT_BDTC150_PL" 2 440 50 260 39 20 10 25 30)
  ("BTTC 1.00 - BNAA 09" "DNIT_BTTC100_PL" 3 470 30 165 32 20 10 25 30)
  ("BTTC 1.20 - BNAA 10" "DNIT_BTTC120_PL" 3 540 40 180 32 20 10 25 30)
  ("BTTC 1.50 - BNAA 11" "DNIT_BTTC150_PL" 3 650 50 260 38 20 10 25 30)
  ;; 2.00 / 2.50 / 3.00 = EXTRAPOLADO (fora das tabelas DNIT)
  ("BSTC 2.00 - EXTRAPOLADO" "DNIT_BSTC200_PL" 1  326  65 345 63 25 10 25 0)
  ("BSTC 2.50 - EXTRAPOLADO" "DNIT_BSTC250_PL" 1  406  85 435 78 25 10 25 0)
  ("BSTC 3.00 - EXTRAPOLADO" "DNIT_BSTC300_PL" 1  488 100 520 94 30 10 25 0)
  ("BDTC 2.00 - EXTRAPOLADO" "DNIT_BDTC200_PL" 2  577  65 345 52 25 10 25 73)
  ("BDTC 2.50 - EXTRAPOLADO" "DNIT_BDTC250_PL" 2  713  85 435 65 25 10 25 83)
  ("BDTC 3.00 - EXTRAPOLADO" "DNIT_BDTC300_PL" 2  849 100 520 78 30 10 25 93)
  ("BTTC 2.00 - EXTRAPOLADO" "DNIT_BTTC200_PL" 3  848  65 345 51 25 10 25 73)
  ("BTTC 2.50 - EXTRAPOLADO" "DNIT_BTTC250_PL" 3 1042  85 435 63 25 10 25 83)
  ("BTTC 3.00 - EXTRAPOLADO" "DNIT_BTTC300_PL" 3 1238 100 520 76 30 10 25 93)))

;;; (estado bloco-base a b c d e)
(setq *bc:dnit-cc* '(
;;; So as secoes quadradas (largura = altura).
  ("BSCC 1.50X1.50 - BNAA 12" "DNIT_BSCC150X150_PL"  185 15 285  237 15)
  ("BSCC 2.00X2.00 - BNAA 14" "DNIT_BSCC200X200_PL"  246 20 355  292 20)
  ("BSCC 2.50X2.50 - BNAA 17" "DNIT_BSCC250X250_PL"  308 25 425  348 25)
  ("BSCC 3.00X3.00 - BNAA 21" "DNIT_BSCC300X300_PL"  369 30 495  404 30)
  ("BDCC 1.50X1.50 - BNAA 22" "DNIT_BDCC150X150_PL"  385 15 285  437 15)
  ("BDCC 2.00X2.00 - BNAA 24" "DNIT_BDCC200X200_PL"  506 20 355  552 20)
  ("BDCC 2.50X2.50 - BNAA 27" "DNIT_BDCC250X250_PL"  628 25 425  668 25)
  ("BDCC 3.00X3.00 - BNAA 31" "DNIT_BDCC300X300_PL"  749 30 495  784 30)
  ("BTCC 1.50X1.50 - BNAA 32" "DNIT_BTCC150X150_PL"  585 15 285  637 15)
  ("BTCC 2.00X2.00 - BNAA 34" "DNIT_BTCC200X200_PL"  766 20 355  812 20)
  ("BTCC 2.50X2.50 - BNAA 37" "DNIT_BTCC250X250_PL"  948 25 425  988 25)
  ("BTCC 3.00X3.00 - BNAA 41" "DNIT_BTCC300X300_PL" 1129 30 495 1164 30)))

;;; Cadastro passa a ser o DNIT V4: (estado bloco-base entidades)
(setq *bc:cadastro* (append
  (mapcar '(lambda (r) (list (car r) (cadr r) (apply 'bc:geo-tc (cddr r)))) *bc:dnit-tc*)
  (mapcar '(lambda (r) (list (car r) (cadr r) (apply 'bc:geo-cc (cddr r)))) *bc:dnit-cc*)))

(defun c:BOCASCADASTRO (/ tp lst i op st pt an)
  (initget "BSTC BDTC BTTC BSCC BDCC BTCC")
  (setq tp (getkword "\nTipo [BSTC/BDTC/BTTC/BSCC/BDCC/BTCC] <BSTC>: "))
  (if (null tp) (setq tp "BSTC"))
  (setq lst (vl-remove-if-not '(lambda (s) (wcmatch (car s) (strcat tp " *"))) *bc:cadastro*)
        i   0)
  (foreach s lst (setq i (1+ i)) (prompt (strcat "\n  " (itoa i) " = " (car s))))
  (initget 6)
  (setq op (getint (strcat "\nOpcao [1-" (itoa (length lst)) "] <1>: ")))
  (if (null op) (setq op 1))
  (if (> op (length lst))
    (prompt "\nOpcao invalida.")
    (progn
      (bc:cad-base)
      (setq st (nth (1- op) lst)
            pt (getpoint "\nCentro da face de chegada da boca: "))
      (if pt
        (progn
          (setq an (getangle pt "\nRotacao <0>: "))
          (if (null an) (setq an 0.0))
          (bc:cad-inserir (cadr st) pt an)))))
  (princ))

(defun c:BOCASCADDIN ()
  (bc:cad-base)
  (bc:bloco-dinamico "BOCA_DNIT_PLANTA_V4" *bc:cadastro* (bc:cad-unidades)) (princ))
(defun c:BOCASADDIN () (c:BOCASCADDIN))
(defun c:BOCASTESTE () (c:BOCASCADDIN))
(princ (strcat "\nDNIT V4: " (itoa (length *bc:cadastro*))
               " variantes BNAA (tubular + celular). BOCASCADDIN cria BOCA_DNIT_PLANTA_V4;"
               " BOCASCADASTRO insere uma variante."))
(princ)
